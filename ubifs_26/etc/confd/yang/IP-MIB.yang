module IP-MIB {
  namespace "http://tail-f.com/ns/mibs/IP-MIB/200602020000Z";
  prefix IP_MIB;
  tailf:id "";
  tailf:snmp-mib-module-name "IP-MIB";
  import ietf-yang-types {
    prefix yang;
  }
  import ietf-inet-types {
    prefix inet;
  }
  import tailf-common {
    prefix tailf;
  }
  import SNMPv2-TC {
    prefix SNMPv2-TC;
  }
  import INET-ADDRESS-MIB {
    prefix INET-ADDRESS-MIB;
  }
  import IF-MIB {
    prefix IF-MIB;
  }
  revision 2006-02-02 {
    description
      "";
  }
  container IP-MIB {
    container ip {
      tailf:snmp-oid "1.3.6.1.2.1.4";
      leaf ipForwarding {
        type ipForwardingType;
        tailf:snmp-oid "1.3.6.1.2.1.4.1";
      }
      leaf ipDefaultTTL {
        type ipDefaultTTLType;
        tailf:snmp-oid "1.3.6.1.2.1.4.2";
      }
      leaf ipInReceives {
        type yang:counter32;
        tailf:snmp-oid "1.3.6.1.2.1.4.3";
        config false;
      }
      leaf ipInHdrErrors {
        type yang:counter32;
        tailf:snmp-oid "1.3.6.1.2.1.4.4";
        config false;
      }
      leaf ipInAddrErrors {
        type yang:counter32;
        tailf:snmp-oid "1.3.6.1.2.1.4.5";
        config false;
      }
      leaf ipForwDatagrams {
        type yang:counter32;
        tailf:snmp-oid "1.3.6.1.2.1.4.6";
        config false;
      }
      leaf ipInUnknownProtos {
        type yang:counter32;
        tailf:snmp-oid "1.3.6.1.2.1.4.7";
        config false;
      }
      leaf ipInDiscards {
        type yang:counter32;
        tailf:snmp-oid "1.3.6.1.2.1.4.8";
        config false;
      }
      leaf ipInDelivers {
        type yang:counter32;
        tailf:snmp-oid "1.3.6.1.2.1.4.9";
        config false;
      }
      leaf ipOutRequests {
        type yang:counter32;
        tailf:snmp-oid "1.3.6.1.2.1.4.10";
        config false;
      }
      leaf ipOutDiscards {
        type yang:counter32;
        tailf:snmp-oid "1.3.6.1.2.1.4.11";
        config false;
      }
      leaf ipOutNoRoutes {
        type yang:counter32;
        tailf:snmp-oid "1.3.6.1.2.1.4.12";
        config false;
      }
      leaf ipReasmTimeout {
        type int32;
        tailf:snmp-oid "1.3.6.1.2.1.4.13";
        config false;
      }
      leaf ipReasmReqds {
        type yang:counter32;
        tailf:snmp-oid "1.3.6.1.2.1.4.14";
        config false;
      }
      leaf ipReasmOKs {
        type yang:counter32;
        tailf:snmp-oid "1.3.6.1.2.1.4.15";
        config false;
      }
      leaf ipReasmFails {
        type yang:counter32;
        tailf:snmp-oid "1.3.6.1.2.1.4.16";
        config false;
      }
      leaf ipFragOKs {
        type yang:counter32;
        tailf:snmp-oid "1.3.6.1.2.1.4.17";
        config false;
      }
      leaf ipFragFails {
        type yang:counter32;
        tailf:snmp-oid "1.3.6.1.2.1.4.18";
        config false;
      }
      leaf ipFragCreates {
        type yang:counter32;
        tailf:snmp-oid "1.3.6.1.2.1.4.19";
        config false;
      }
      leaf ipRoutingDiscards {
        type yang:counter32;
        tailf:snmp-oid "1.3.6.1.2.1.4.23";
        config false;
      }
      leaf ipv6IpForwarding {
        type ipv6IpForwardingType;
        tailf:snmp-oid "1.3.6.1.2.1.4.25";
      }
      leaf ipv6IpDefaultHopLimit {
        type ipv6IpDefaultHopLimitType;
        tailf:snmp-oid "1.3.6.1.2.1.4.26";
      }
      leaf ipv4InterfaceTableLastChange {
        type yang:timestamp;
        tailf:snmp-oid "1.3.6.1.2.1.4.27";
        config false;
      }
      leaf ipv6InterfaceTableLastChange {
        type yang:timestamp;
        tailf:snmp-oid "1.3.6.1.2.1.4.29";
        config false;
      }
    }
    container ipTrafficStats {
      tailf:snmp-oid "1.3.6.1.2.1.4.31";
      config false;
      leaf ipIfStatsTableLastChange {
        type yang:timestamp;
        tailf:snmp-oid "1.3.6.1.2.1.4.31.2";
        config false;
      }
    }
    container icmp {
      tailf:snmp-oid "1.3.6.1.2.1.5";
      config false;
      leaf icmpInMsgs {
        type yang:counter32;
        tailf:snmp-oid "1.3.6.1.2.1.5.1";
        config false;
      }
      leaf icmpInErrors {
        type yang:counter32;
        tailf:snmp-oid "1.3.6.1.2.1.5.2";
        config false;
      }
      leaf icmpInDestUnreachs {
        type yang:counter32;
        tailf:snmp-oid "1.3.6.1.2.1.5.3";
        config false;
      }
      leaf icmpInTimeExcds {
        type yang:counter32;
        tailf:snmp-oid "1.3.6.1.2.1.5.4";
        config false;
      }
      leaf icmpInParmProbs {
        type yang:counter32;
        tailf:snmp-oid "1.3.6.1.2.1.5.5";
        config false;
      }
      leaf icmpInSrcQuenchs {
        type yang:counter32;
        tailf:snmp-oid "1.3.6.1.2.1.5.6";
        config false;
      }
      leaf icmpInRedirects {
        type yang:counter32;
        tailf:snmp-oid "1.3.6.1.2.1.5.7";
        config false;
      }
      leaf icmpInEchos {
        type yang:counter32;
        tailf:snmp-oid "1.3.6.1.2.1.5.8";
        config false;
      }
      leaf icmpInEchoReps {
        type yang:counter32;
        tailf:snmp-oid "1.3.6.1.2.1.5.9";
        config false;
      }
      leaf icmpInTimestamps {
        type yang:counter32;
        tailf:snmp-oid "1.3.6.1.2.1.5.10";
        config false;
      }
      leaf icmpInTimestampReps {
        type yang:counter32;
        tailf:snmp-oid "1.3.6.1.2.1.5.11";
        config false;
      }
      leaf icmpInAddrMasks {
        type yang:counter32;
        tailf:snmp-oid "1.3.6.1.2.1.5.12";
        config false;
      }
      leaf icmpInAddrMaskReps {
        type yang:counter32;
        tailf:snmp-oid "1.3.6.1.2.1.5.13";
        config false;
      }
      leaf icmpOutMsgs {
        type yang:counter32;
        tailf:snmp-oid "1.3.6.1.2.1.5.14";
        config false;
      }
      leaf icmpOutErrors {
        type yang:counter32;
        tailf:snmp-oid "1.3.6.1.2.1.5.15";
        config false;
      }
      leaf icmpOutDestUnreachs {
        type yang:counter32;
        tailf:snmp-oid "1.3.6.1.2.1.5.16";
        config false;
      }
      leaf icmpOutTimeExcds {
        type yang:counter32;
        tailf:snmp-oid "1.3.6.1.2.1.5.17";
        config false;
      }
      leaf icmpOutParmProbs {
        type yang:counter32;
        tailf:snmp-oid "1.3.6.1.2.1.5.18";
        config false;
      }
      leaf icmpOutSrcQuenchs {
        type yang:counter32;
        tailf:snmp-oid "1.3.6.1.2.1.5.19";
        config false;
      }
      leaf icmpOutRedirects {
        type yang:counter32;
        tailf:snmp-oid "1.3.6.1.2.1.5.20";
        config false;
      }
      leaf icmpOutEchos {
        type yang:counter32;
        tailf:snmp-oid "1.3.6.1.2.1.5.21";
        config false;
      }
      leaf icmpOutEchoReps {
        type yang:counter32;
        tailf:snmp-oid "1.3.6.1.2.1.5.22";
        config false;
      }
      leaf icmpOutTimestamps {
        type yang:counter32;
        tailf:snmp-oid "1.3.6.1.2.1.5.23";
        config false;
      }
      leaf icmpOutTimestampReps {
        type yang:counter32;
        tailf:snmp-oid "1.3.6.1.2.1.5.24";
        config false;
      }
      leaf icmpOutAddrMasks {
        type yang:counter32;
        tailf:snmp-oid "1.3.6.1.2.1.5.25";
        config false;
      }
      leaf icmpOutAddrMaskReps {
        type yang:counter32;
        tailf:snmp-oid "1.3.6.1.2.1.5.26";
        config false;
      }
    }
    container ipAddrTable {
      config false;
      list ipAddrEntry {
        key "ipAdEntAddr";
        tailf:sort-order "snmp";
        config false;
        tailf:snmp-oid "1.3.6.1.2.1.4.20";
        leaf ipAdEntAddr {
          type inet:ipv4-address;
          tailf:snmp-oid "1.3.6.1.2.1.4.20.1.1";
        }
        leaf ipAdEntIfIndex {
          type ipAdEntIfIndexType;
          tailf:snmp-oid "1.3.6.1.2.1.4.20.1.2";
          config false;
        }
        leaf ipAdEntNetMask {
          type inet:ipv4-address;
          tailf:snmp-oid "1.3.6.1.2.1.4.20.1.3";
          config false;
        }
        leaf ipAdEntBcastAddr {
          type ipAdEntBcastAddrType;
          tailf:snmp-oid "1.3.6.1.2.1.4.20.1.4";
          config false;
        }
        leaf ipAdEntReasmMaxSize {
          type ipAdEntReasmMaxSizeType;
          tailf:snmp-oid "1.3.6.1.2.1.4.20.1.5";
          config false;
        }
      }
    }
    container ipNetToMediaTable {
      list ipNetToMediaEntry {
        key "ipNetToMediaIfIndex ipNetToMediaNetAddress";
        tailf:sort-order "snmp";
        tailf:snmp-oid "1.3.6.1.2.1.4.22";
        leaf ipNetToMediaIfIndex {
          type ipNetToMediaIfIndexType;
          tailf:snmp-oid "1.3.6.1.2.1.4.22.1.1";
        }
        leaf ipNetToMediaNetAddress {
          type inet:ipv4-address;
          tailf:snmp-oid "1.3.6.1.2.1.4.22.1.3";
        }
        leaf ipNetToMediaPhysAddress {
          type ipNetToMediaPhysAddressType;
          tailf:snmp-oid "1.3.6.1.2.1.4.22.1.2";
        }
        leaf ipNetToMediaType {
          type ipNetToMediaTypeType;
          tailf:snmp-oid "1.3.6.1.2.1.4.22.1.4";
        }
      }
    }
    container ipv4InterfaceTable {
      list ipv4InterfaceEntry {
        key "ipv4InterfaceIfIndex";
        tailf:sort-order "snmp";
        tailf:snmp-oid "1.3.6.1.2.1.4.28";
        leaf ipv4InterfaceIfIndex {
          type IF-MIB:InterfaceIndex;
          tailf:snmp-oid "1.3.6.1.2.1.4.28.1.1";
        }
        leaf ipv4InterfaceReasmMaxSize {
          type ipv4InterfaceReasmMaxSizeType;
          tailf:snmp-oid "1.3.6.1.2.1.4.28.1.2";
          config false;
        }
        leaf ipv4InterfaceEnableStatus {
          type ipv4InterfaceEnableStatusType;
          tailf:snmp-oid "1.3.6.1.2.1.4.28.1.3";
        }
        leaf ipv4InterfaceRetransmitTime {
          type uint32;
          tailf:snmp-oid "1.3.6.1.2.1.4.28.1.4";
          config false;
        }
      }
    }
    container ipv6InterfaceTable {
      list ipv6InterfaceEntry {
        key "ipv6InterfaceIfIndex";
        tailf:sort-order "snmp";
        tailf:snmp-oid "1.3.6.1.2.1.4.30";
        leaf ipv6InterfaceIfIndex {
          type IF-MIB:InterfaceIndex;
          tailf:snmp-oid "1.3.6.1.2.1.4.30.1.1";
        }
        leaf ipv6InterfaceReasmMaxSize {
          type ipv6InterfaceReasmMaxSizeType;
          tailf:snmp-oid "1.3.6.1.2.1.4.30.1.2";
          config false;
        }
        leaf ipv6InterfaceIdentifier {
          type Ipv6AddressIfIdentifierTC;
          tailf:snmp-oid "1.3.6.1.2.1.4.30.1.3";
          config false;
        }
        leaf ipv6InterfaceEnableStatus {
          type ipv6InterfaceEnableStatusType;
          tailf:snmp-oid "1.3.6.1.2.1.4.30.1.5";
        }
        leaf ipv6InterfaceReachableTime {
          type uint32;
          tailf:snmp-oid "1.3.6.1.2.1.4.30.1.6";
          config false;
        }
        leaf ipv6InterfaceRetransmitTime {
          type uint32;
          tailf:snmp-oid "1.3.6.1.2.1.4.30.1.7";
          config false;
        }
        leaf ipv6InterfaceForwarding {
          type ipv6InterfaceForwardingType;
          tailf:snmp-oid "1.3.6.1.2.1.4.30.1.8";
        }
      }
    }
    container ipSystemStatsTable {
      config false;
      list ipSystemStatsEntry {
        key "ipSystemStatsIPVersion";
        tailf:sort-order "snmp";
        config false;
        tailf:snmp-oid "1.3.6.1.2.1.4.31.1";
        leaf ipSystemStatsIPVersion {
          type INET-ADDRESS-MIB:InetVersion;
          tailf:snmp-oid "1.3.6.1.2.1.4.31.1.1.1";
        }
        leaf ipSystemStatsInReceives {
          type yang:counter32;
          tailf:snmp-oid "1.3.6.1.2.1.4.31.1.1.3";
          config false;
        }
        leaf ipSystemStatsHCInReceives {
          type yang:counter64;
          tailf:snmp-oid "1.3.6.1.2.1.4.31.1.1.4";
          config false;
        }
        leaf ipSystemStatsInOctets {
          type yang:counter32;
          tailf:snmp-oid "1.3.6.1.2.1.4.31.1.1.5";
          config false;
        }
        leaf ipSystemStatsHCInOctets {
          type yang:counter64;
          tailf:snmp-oid "1.3.6.1.2.1.4.31.1.1.6";
          config false;
        }
        leaf ipSystemStatsInHdrErrors {
          type yang:counter32;
          tailf:snmp-oid "1.3.6.1.2.1.4.31.1.1.7";
          config false;
        }
        leaf ipSystemStatsInNoRoutes {
          type yang:counter32;
          tailf:snmp-oid "1.3.6.1.2.1.4.31.1.1.8";
          config false;
        }
        leaf ipSystemStatsInAddrErrors {
          type yang:counter32;
          tailf:snmp-oid "1.3.6.1.2.1.4.31.1.1.9";
          config false;
        }
        leaf ipSystemStatsInUnknownProtos {
          type yang:counter32;
          tailf:snmp-oid "1.3.6.1.2.1.4.31.1.1.10";
          config false;
        }
        leaf ipSystemStatsInTruncatedPkts {
          type yang:counter32;
          tailf:snmp-oid "1.3.6.1.2.1.4.31.1.1.11";
          config false;
        }
        leaf ipSystemStatsInForwDatagrams {
          type yang:counter32;
          tailf:snmp-oid "1.3.6.1.2.1.4.31.1.1.12";
          config false;
        }
        leaf ipSystemStatsHCInForwDatagrams {
          type yang:counter64;
          tailf:snmp-oid "1.3.6.1.2.1.4.31.1.1.13";
          config false;
        }
        leaf ipSystemStatsReasmReqds {
          type yang:counter32;
          tailf:snmp-oid "1.3.6.1.2.1.4.31.1.1.14";
          config false;
        }
        leaf ipSystemStatsReasmOKs {
          type yang:counter32;
          tailf:snmp-oid "1.3.6.1.2.1.4.31.1.1.15";
          config false;
        }
        leaf ipSystemStatsReasmFails {
          type yang:counter32;
          tailf:snmp-oid "1.3.6.1.2.1.4.31.1.1.16";
          config false;
        }
        leaf ipSystemStatsInDiscards {
          type yang:counter32;
          tailf:snmp-oid "1.3.6.1.2.1.4.31.1.1.17";
          config false;
        }
        leaf ipSystemStatsInDelivers {
          type yang:counter32;
          tailf:snmp-oid "1.3.6.1.2.1.4.31.1.1.18";
          config false;
        }
        leaf ipSystemStatsHCInDelivers {
          type yang:counter64;
          tailf:snmp-oid "1.3.6.1.2.1.4.31.1.1.19";
          config false;
        }
        leaf ipSystemStatsOutRequests {
          type yang:counter32;
          tailf:snmp-oid "1.3.6.1.2.1.4.31.1.1.20";
          config false;
        }
        leaf ipSystemStatsHCOutRequests {
          type yang:counter64;
          tailf:snmp-oid "1.3.6.1.2.1.4.31.1.1.21";
          config false;
        }
        leaf ipSystemStatsOutNoRoutes {
          type yang:counter32;
          tailf:snmp-oid "1.3.6.1.2.1.4.31.1.1.22";
          config false;
        }
        leaf ipSystemStatsOutForwDatagrams {
          type yang:counter32;
          tailf:snmp-oid "1.3.6.1.2.1.4.31.1.1.23";
          config false;
        }
        leaf ipSystemStatsHCOutForwDatagrams {
          type yang:counter64;
          tailf:snmp-oid "1.3.6.1.2.1.4.31.1.1.24";
          config false;
        }
        leaf ipSystemStatsOutDiscards {
          type yang:counter32;
          tailf:snmp-oid "1.3.6.1.2.1.4.31.1.1.25";
          config false;
        }
        leaf ipSystemStatsOutFragReqds {
          type yang:counter32;
          tailf:snmp-oid "1.3.6.1.2.1.4.31.1.1.26";
          config false;
        }
        leaf ipSystemStatsOutFragOKs {
          type yang:counter32;
          tailf:snmp-oid "1.3.6.1.2.1.4.31.1.1.27";
          config false;
        }
        leaf ipSystemStatsOutFragFails {
          type yang:counter32;
          tailf:snmp-oid "1.3.6.1.2.1.4.31.1.1.28";
          config false;
        }
        leaf ipSystemStatsOutFragCreates {
          type yang:counter32;
          tailf:snmp-oid "1.3.6.1.2.1.4.31.1.1.29";
          config false;
        }
        leaf ipSystemStatsOutTransmits {
          type yang:counter32;
          tailf:snmp-oid "1.3.6.1.2.1.4.31.1.1.30";
          config false;
        }
        leaf ipSystemStatsHCOutTransmits {
          type yang:counter64;
          tailf:snmp-oid "1.3.6.1.2.1.4.31.1.1.31";
          config false;
        }
        leaf ipSystemStatsOutOctets {
          type yang:counter32;
          tailf:snmp-oid "1.3.6.1.2.1.4.31.1.1.32";
          config false;
        }
        leaf ipSystemStatsHCOutOctets {
          type yang:counter64;
          tailf:snmp-oid "1.3.6.1.2.1.4.31.1.1.33";
          config false;
        }
        leaf ipSystemStatsInMcastPkts {
          type yang:counter32;
          tailf:snmp-oid "1.3.6.1.2.1.4.31.1.1.34";
          config false;
        }
        leaf ipSystemStatsHCInMcastPkts {
          type yang:counter64;
          tailf:snmp-oid "1.3.6.1.2.1.4.31.1.1.35";
          config false;
        }
        leaf ipSystemStatsInMcastOctets {
          type yang:counter32;
          tailf:snmp-oid "1.3.6.1.2.1.4.31.1.1.36";
          config false;
        }
        leaf ipSystemStatsHCInMcastOctets {
          type yang:counter64;
          tailf:snmp-oid "1.3.6.1.2.1.4.31.1.1.37";
          config false;
        }
        leaf ipSystemStatsOutMcastPkts {
          type yang:counter32;
          tailf:snmp-oid "1.3.6.1.2.1.4.31.1.1.38";
          config false;
        }
        leaf ipSystemStatsHCOutMcastPkts {
          type yang:counter64;
          tailf:snmp-oid "1.3.6.1.2.1.4.31.1.1.39";
          config false;
        }
        leaf ipSystemStatsOutMcastOctets {
          type yang:counter32;
          tailf:snmp-oid "1.3.6.1.2.1.4.31.1.1.40";
          config false;
        }
        leaf ipSystemStatsHCOutMcastOctets {
          type yang:counter64;
          tailf:snmp-oid "1.3.6.1.2.1.4.31.1.1.41";
          config false;
        }
        leaf ipSystemStatsInBcastPkts {
          type yang:counter32;
          tailf:snmp-oid "1.3.6.1.2.1.4.31.1.1.42";
          config false;
        }
        leaf ipSystemStatsHCInBcastPkts {
          type yang:counter64;
          tailf:snmp-oid "1.3.6.1.2.1.4.31.1.1.43";
          config false;
        }
        leaf ipSystemStatsOutBcastPkts {
          type yang:counter32;
          tailf:snmp-oid "1.3.6.1.2.1.4.31.1.1.44";
          config false;
        }
        leaf ipSystemStatsHCOutBcastPkts {
          type yang:counter64;
          tailf:snmp-oid "1.3.6.1.2.1.4.31.1.1.45";
          config false;
        }
        leaf ipSystemStatsDiscontinuityTime {
          type yang:timestamp;
          tailf:snmp-oid "1.3.6.1.2.1.4.31.1.1.46";
          config false;
        }
        leaf ipSystemStatsRefreshRate {
          type uint32;
          tailf:snmp-oid "1.3.6.1.2.1.4.31.1.1.47";
          config false;
        }
      }
    }
    container ipIfStatsTable {
      config false;
      list ipIfStatsEntry {
        key "ipIfStatsIPVersion ipIfStatsIfIndex";
        tailf:sort-order "snmp";
        config false;
        tailf:snmp-oid "1.3.6.1.2.1.4.31.3";
        leaf ipIfStatsIPVersion {
          type INET-ADDRESS-MIB:InetVersion;
          tailf:snmp-oid "1.3.6.1.2.1.4.31.3.1.1";
        }
        leaf ipIfStatsIfIndex {
          type IF-MIB:InterfaceIndex;
          tailf:snmp-oid "1.3.6.1.2.1.4.31.3.1.2";
        }
        leaf ipIfStatsInReceives {
          type yang:counter32;
          tailf:snmp-oid "1.3.6.1.2.1.4.31.3.1.3";
          config false;
        }
        leaf ipIfStatsHCInReceives {
          type yang:counter64;
          tailf:snmp-oid "1.3.6.1.2.1.4.31.3.1.4";
          config false;
        }
        leaf ipIfStatsInOctets {
          type yang:counter32;
          tailf:snmp-oid "1.3.6.1.2.1.4.31.3.1.5";
          config false;
        }
        leaf ipIfStatsHCInOctets {
          type yang:counter64;
          tailf:snmp-oid "1.3.6.1.2.1.4.31.3.1.6";
          config false;
        }
        leaf ipIfStatsInHdrErrors {
          type yang:counter32;
          tailf:snmp-oid "1.3.6.1.2.1.4.31.3.1.7";
          config false;
        }
        leaf ipIfStatsInNoRoutes {
          type yang:counter32;
          tailf:snmp-oid "1.3.6.1.2.1.4.31.3.1.8";
          config false;
        }
        leaf ipIfStatsInAddrErrors {
          type yang:counter32;
          tailf:snmp-oid "1.3.6.1.2.1.4.31.3.1.9";
          config false;
        }
        leaf ipIfStatsInUnknownProtos {
          type yang:counter32;
          tailf:snmp-oid "1.3.6.1.2.1.4.31.3.1.10";
          config false;
        }
        leaf ipIfStatsInTruncatedPkts {
          type yang:counter32;
          tailf:snmp-oid "1.3.6.1.2.1.4.31.3.1.11";
          config false;
        }
        leaf ipIfStatsInForwDatagrams {
          type yang:counter32;
          tailf:snmp-oid "1.3.6.1.2.1.4.31.3.1.12";
          config false;
        }
        leaf ipIfStatsHCInForwDatagrams {
          type yang:counter64;
          tailf:snmp-oid "1.3.6.1.2.1.4.31.3.1.13";
          config false;
        }
        leaf ipIfStatsReasmReqds {
          type yang:counter32;
          tailf:snmp-oid "1.3.6.1.2.1.4.31.3.1.14";
          config false;
        }
        leaf ipIfStatsReasmOKs {
          type yang:counter32;
          tailf:snmp-oid "1.3.6.1.2.1.4.31.3.1.15";
          config false;
        }
        leaf ipIfStatsReasmFails {
          type yang:counter32;
          tailf:snmp-oid "1.3.6.1.2.1.4.31.3.1.16";
          config false;
        }
        leaf ipIfStatsInDiscards {
          type yang:counter32;
          tailf:snmp-oid "1.3.6.1.2.1.4.31.3.1.17";
          config false;
        }
        leaf ipIfStatsInDelivers {
          type yang:counter32;
          tailf:snmp-oid "1.3.6.1.2.1.4.31.3.1.18";
          config false;
        }
        leaf ipIfStatsHCInDelivers {
          type yang:counter64;
          tailf:snmp-oid "1.3.6.1.2.1.4.31.3.1.19";
          config false;
        }
        leaf ipIfStatsOutRequests {
          type yang:counter32;
          tailf:snmp-oid "1.3.6.1.2.1.4.31.3.1.20";
          config false;
        }
        leaf ipIfStatsHCOutRequests {
          type yang:counter64;
          tailf:snmp-oid "1.3.6.1.2.1.4.31.3.1.21";
          config false;
        }
        leaf ipIfStatsOutForwDatagrams {
          type yang:counter32;
          tailf:snmp-oid "1.3.6.1.2.1.4.31.3.1.23";
          config false;
        }
        leaf ipIfStatsHCOutForwDatagrams {
          type yang:counter64;
          tailf:snmp-oid "1.3.6.1.2.1.4.31.3.1.24";
          config false;
        }
        leaf ipIfStatsOutDiscards {
          type yang:counter32;
          tailf:snmp-oid "1.3.6.1.2.1.4.31.3.1.25";
          config false;
        }
        leaf ipIfStatsOutFragReqds {
          type yang:counter32;
          tailf:snmp-oid "1.3.6.1.2.1.4.31.3.1.26";
          config false;
        }
        leaf ipIfStatsOutFragOKs {
          type yang:counter32;
          tailf:snmp-oid "1.3.6.1.2.1.4.31.3.1.27";
          config false;
        }
        leaf ipIfStatsOutFragFails {
          type yang:counter32;
          tailf:snmp-oid "1.3.6.1.2.1.4.31.3.1.28";
          config false;
        }
        leaf ipIfStatsOutFragCreates {
          type yang:counter32;
          tailf:snmp-oid "1.3.6.1.2.1.4.31.3.1.29";
          config false;
        }
        leaf ipIfStatsOutTransmits {
          type yang:counter32;
          tailf:snmp-oid "1.3.6.1.2.1.4.31.3.1.30";
          config false;
        }
        leaf ipIfStatsHCOutTransmits {
          type yang:counter64;
          tailf:snmp-oid "1.3.6.1.2.1.4.31.3.1.31";
          config false;
        }
        leaf ipIfStatsOutOctets {
          type yang:counter32;
          tailf:snmp-oid "1.3.6.1.2.1.4.31.3.1.32";
          config false;
        }
        leaf ipIfStatsHCOutOctets {
          type yang:counter64;
          tailf:snmp-oid "1.3.6.1.2.1.4.31.3.1.33";
          config false;
        }
        leaf ipIfStatsInMcastPkts {
          type yang:counter32;
          tailf:snmp-oid "1.3.6.1.2.1.4.31.3.1.34";
          config false;
        }
        leaf ipIfStatsHCInMcastPkts {
          type yang:counter64;
          tailf:snmp-oid "1.3.6.1.2.1.4.31.3.1.35";
          config false;
        }
        leaf ipIfStatsInMcastOctets {
          type yang:counter32;
          tailf:snmp-oid "1.3.6.1.2.1.4.31.3.1.36";
          config false;
        }
        leaf ipIfStatsHCInMcastOctets {
          type yang:counter64;
          tailf:snmp-oid "1.3.6.1.2.1.4.31.3.1.37";
          config false;
        }
        leaf ipIfStatsOutMcastPkts {
          type yang:counter32;
          tailf:snmp-oid "1.3.6.1.2.1.4.31.3.1.38";
          config false;
        }
        leaf ipIfStatsHCOutMcastPkts {
          type yang:counter64;
          tailf:snmp-oid "1.3.6.1.2.1.4.31.3.1.39";
          config false;
        }
        leaf ipIfStatsOutMcastOctets {
          type yang:counter32;
          tailf:snmp-oid "1.3.6.1.2.1.4.31.3.1.40";
          config false;
        }
        leaf ipIfStatsHCOutMcastOctets {
          type yang:counter64;
          tailf:snmp-oid "1.3.6.1.2.1.4.31.3.1.41";
          config false;
        }
        leaf ipIfStatsInBcastPkts {
          type yang:counter32;
          tailf:snmp-oid "1.3.6.1.2.1.4.31.3.1.42";
          config false;
        }
        leaf ipIfStatsHCInBcastPkts {
          type yang:counter64;
          tailf:snmp-oid "1.3.6.1.2.1.4.31.3.1.43";
          config false;
        }
        leaf ipIfStatsOutBcastPkts {
          type yang:counter32;
          tailf:snmp-oid "1.3.6.1.2.1.4.31.3.1.44";
          config false;
        }
        leaf ipIfStatsHCOutBcastPkts {
          type yang:counter64;
          tailf:snmp-oid "1.3.6.1.2.1.4.31.3.1.45";
          config false;
        }
        leaf ipIfStatsDiscontinuityTime {
          type yang:timestamp;
          tailf:snmp-oid "1.3.6.1.2.1.4.31.3.1.46";
          config false;
        }
        leaf ipIfStatsRefreshRate {
          type uint32;
          tailf:snmp-oid "1.3.6.1.2.1.4.31.3.1.47";
          config false;
        }
      }
    }
    container ipAddressPrefixTable {
      config false;
      list ipAddressPrefixEntry {
        key "ipAddressPrefixIfIndex ipAddressPrefixType ipAddressPrefixPrefix ipAddressPrefixLength";
        tailf:sort-order "snmp";
        config false;
        tailf:snmp-oid "1.3.6.1.2.1.4.32";
        leaf ipAddressPrefixIfIndex {
          type IF-MIB:InterfaceIndex;
          tailf:snmp-oid "1.3.6.1.2.1.4.32.1.1";
        }
        leaf ipAddressPrefixType {
          type INET-ADDRESS-MIB:InetAddressType;
          tailf:snmp-oid "1.3.6.1.2.1.4.32.1.2";
        }
        leaf ipAddressPrefixPrefix {
          type INET-ADDRESS-MIB:InetAddress;
          tailf:snmp-oid "1.3.6.1.2.1.4.32.1.3";
        }
        leaf ipAddressPrefixLength {
          type INET-ADDRESS-MIB:InetAddressPrefixLength;
          tailf:snmp-oid "1.3.6.1.2.1.4.32.1.4";
        }
        leaf ipAddressPrefixOrigin {
          type IpAddressPrefixOriginTC;
          tailf:snmp-oid "1.3.6.1.2.1.4.32.1.5";
          config false;
        }
        leaf ipAddressPrefixOnLinkFlag {
          type SNMPv2-TC:TruthValue;
          tailf:snmp-oid "1.3.6.1.2.1.4.32.1.6";
          config false;
        }
        leaf ipAddressPrefixAutonomousFlag {
          type SNMPv2-TC:TruthValue;
          tailf:snmp-oid "1.3.6.1.2.1.4.32.1.7";
          config false;
        }
        leaf ipAddressPrefixAdvPreferredLifetime {
          type uint32;
          tailf:snmp-oid "1.3.6.1.2.1.4.32.1.8";
          config false;
        }
        leaf ipAddressPrefixAdvValidLifetime {
          type uint32;
          tailf:snmp-oid "1.3.6.1.2.1.4.32.1.9";
          config false;
        }
      }
    }
    container ipAddressTable {
      list ipAddressEntry {
        key "ipAddressAddrType ipAddressAddr";
        tailf:sort-order "snmp";
        tailf:snmp-oid "1.3.6.1.2.1.4.34";
        leaf ipAddressAddrType {
          type INET-ADDRESS-MIB:InetAddressType;
          tailf:snmp-oid "1.3.6.1.2.1.4.34.1.1";
        }
        leaf ipAddressAddr {
          type INET-ADDRESS-MIB:InetAddress;
          tailf:snmp-oid "1.3.6.1.2.1.4.34.1.2";
        }
        leaf ipAddressIfIndex {
          type IF-MIB:InterfaceIndex;
          tailf:snmp-oid "1.3.6.1.2.1.4.34.1.3";
        }
        leaf ipAddressType {
          type ipAddressTypeType;
          tailf:snmp-oid "1.3.6.1.2.1.4.34.1.4";
          default "unicast";
        }
        leaf ipAddressPrefix {
          type SNMPv2-TC:RowPointer;
          tailf:snmp-oid "1.3.6.1.2.1.4.34.1.5";
          config false;
        }
        leaf ipAddressOrigin {
          type IpAddressOriginTC;
          tailf:snmp-oid "1.3.6.1.2.1.4.34.1.6";
          config false;
        }
        leaf ipAddressStatus {
          type IpAddressStatusTC;
          tailf:snmp-oid "1.3.6.1.2.1.4.34.1.7";
          default "preferred";
        }
        leaf ipAddressCreated {
          type yang:timestamp;
          tailf:snmp-oid "1.3.6.1.2.1.4.34.1.8";
          config false;
        }
        leaf ipAddressLastChanged {
          type yang:timestamp;
          tailf:snmp-oid "1.3.6.1.2.1.4.34.1.9";
          config false;
        }
        leaf ipAddressStorageType {
          type SNMPv2-TC:StorageType;
          tailf:snmp-oid "1.3.6.1.2.1.4.34.1.11";
          default "volatile";
        }
      }
    }
    container ipNetToPhysicalTable {
      list ipNetToPhysicalEntry {
        key "ipNetToPhysicalIfIndex ipNetToPhysicalNetAddressType ipNetToPhysicalNetAddress";
        tailf:sort-order "snmp";
        tailf:snmp-oid "1.3.6.1.2.1.4.35";
        leaf ipNetToPhysicalIfIndex {
          type IF-MIB:InterfaceIndex;
          tailf:snmp-oid "1.3.6.1.2.1.4.35.1.1";
        }
        leaf ipNetToPhysicalNetAddressType {
          type INET-ADDRESS-MIB:InetAddressType;
          tailf:snmp-oid "1.3.6.1.2.1.4.35.1.2";
        }
        leaf ipNetToPhysicalNetAddress {
          type INET-ADDRESS-MIB:InetAddress;
          tailf:snmp-oid "1.3.6.1.2.1.4.35.1.3";
        }
        leaf ipNetToPhysicalPhysAddress {
          type ipNetToPhysicalPhysAddressType;
          tailf:snmp-oid "1.3.6.1.2.1.4.35.1.4";
        }
        leaf ipNetToPhysicalLastUpdated {
          type yang:timestamp;
          tailf:snmp-oid "1.3.6.1.2.1.4.35.1.5";
          config false;
        }
        leaf ipNetToPhysicalType {
          type ipNetToPhysicalTypeType;
          tailf:snmp-oid "1.3.6.1.2.1.4.35.1.6";
          default "static";
        }
        leaf ipNetToPhysicalState {
          type ipNetToPhysicalStateType;
          tailf:snmp-oid "1.3.6.1.2.1.4.35.1.7";
          config false;
        }
      }
    }
    container ipv6ScopeZoneIndexTable {
      config false;
      list ipv6ScopeZoneIndexEntry {
        key "ipv6ScopeZoneIndexIfIndex";
        tailf:sort-order "snmp";
        config false;
        tailf:snmp-oid "1.3.6.1.2.1.4.36";
        leaf ipv6ScopeZoneIndexIfIndex {
          type IF-MIB:InterfaceIndex;
          tailf:snmp-oid "1.3.6.1.2.1.4.36.1.1";
        }
        leaf ipv6ScopeZoneIndexLinkLocal {
          type INET-ADDRESS-MIB:InetZoneIndex;
          tailf:snmp-oid "1.3.6.1.2.1.4.36.1.2";
          config false;
        }
        leaf ipv6ScopeZoneIndex3 {
          type INET-ADDRESS-MIB:InetZoneIndex;
          tailf:snmp-oid "1.3.6.1.2.1.4.36.1.3";
          config false;
        }
        leaf ipv6ScopeZoneIndexAdminLocal {
          type INET-ADDRESS-MIB:InetZoneIndex;
          tailf:snmp-oid "1.3.6.1.2.1.4.36.1.4";
          config false;
        }
        leaf ipv6ScopeZoneIndexSiteLocal {
          type INET-ADDRESS-MIB:InetZoneIndex;
          tailf:snmp-oid "1.3.6.1.2.1.4.36.1.5";
          config false;
        }
        leaf ipv6ScopeZoneIndex6 {
          type INET-ADDRESS-MIB:InetZoneIndex;
          tailf:snmp-oid "1.3.6.1.2.1.4.36.1.6";
          config false;
        }
        leaf ipv6ScopeZoneIndex7 {
          type INET-ADDRESS-MIB:InetZoneIndex;
          tailf:snmp-oid "1.3.6.1.2.1.4.36.1.7";
          config false;
        }
        leaf ipv6ScopeZoneIndexOrganizationLocal {
          type INET-ADDRESS-MIB:InetZoneIndex;
          tailf:snmp-oid "1.3.6.1.2.1.4.36.1.8";
          config false;
        }
        leaf ipv6ScopeZoneIndex9 {
          type INET-ADDRESS-MIB:InetZoneIndex;
          tailf:snmp-oid "1.3.6.1.2.1.4.36.1.9";
          config false;
        }
        leaf ipv6ScopeZoneIndexA {
          type INET-ADDRESS-MIB:InetZoneIndex;
          tailf:snmp-oid "1.3.6.1.2.1.4.36.1.10";
          config false;
        }
        leaf ipv6ScopeZoneIndexB {
          type INET-ADDRESS-MIB:InetZoneIndex;
          tailf:snmp-oid "1.3.6.1.2.1.4.36.1.11";
          config false;
        }
        leaf ipv6ScopeZoneIndexC {
          type INET-ADDRESS-MIB:InetZoneIndex;
          tailf:snmp-oid "1.3.6.1.2.1.4.36.1.12";
          config false;
        }
        leaf ipv6ScopeZoneIndexD {
          type INET-ADDRESS-MIB:InetZoneIndex;
          tailf:snmp-oid "1.3.6.1.2.1.4.36.1.13";
          config false;
        }
      }
    }
    container ipDefaultRouterTable {
      config false;
      list ipDefaultRouterEntry {
        key "ipDefaultRouterAddressType ipDefaultRouterAddress ipDefaultRouterIfIndex";
        tailf:sort-order "snmp";
        config false;
        tailf:snmp-oid "1.3.6.1.2.1.4.37";
        leaf ipDefaultRouterAddressType {
          type INET-ADDRESS-MIB:InetAddressType;
          tailf:snmp-oid "1.3.6.1.2.1.4.37.1.1";
        }
        leaf ipDefaultRouterAddress {
          type INET-ADDRESS-MIB:InetAddress;
          tailf:snmp-oid "1.3.6.1.2.1.4.37.1.2";
        }
        leaf ipDefaultRouterIfIndex {
          type IF-MIB:InterfaceIndex;
          tailf:snmp-oid "1.3.6.1.2.1.4.37.1.3";
        }
        leaf ipDefaultRouterLifetime {
          type ipDefaultRouterLifetimeType;
          tailf:snmp-oid "1.3.6.1.2.1.4.37.1.4";
          config false;
        }
        leaf ipDefaultRouterPreference {
          type ipDefaultRouterPreferenceType;
          tailf:snmp-oid "1.3.6.1.2.1.4.37.1.5";
          config false;
        }
      }
    }
    container ipv6RouterAdvertTable {
      list ipv6RouterAdvertEntry {
        key "ipv6RouterAdvertIfIndex";
        tailf:sort-order "snmp";
        tailf:snmp-oid "1.3.6.1.2.1.4.39";
        leaf ipv6RouterAdvertIfIndex {
          type IF-MIB:InterfaceIndex;
          tailf:snmp-oid "1.3.6.1.2.1.4.39.1.1";
        }
        leaf ipv6RouterAdvertSendAdverts {
          type SNMPv2-TC:TruthValue;
          tailf:snmp-oid "1.3.6.1.2.1.4.39.1.2";
          default "false";
        }
        leaf ipv6RouterAdvertMaxInterval {
          type ipv6RouterAdvertMaxIntervalType;
          tailf:snmp-oid "1.3.6.1.2.1.4.39.1.3";
          default "600";
        }
        leaf ipv6RouterAdvertMinInterval {
          type ipv6RouterAdvertMinIntervalType;
          tailf:snmp-oid "1.3.6.1.2.1.4.39.1.4";
        }
        leaf ipv6RouterAdvertManagedFlag {
          type SNMPv2-TC:TruthValue;
          tailf:snmp-oid "1.3.6.1.2.1.4.39.1.5";
          default "false";
        }
        leaf ipv6RouterAdvertOtherConfigFlag {
          type SNMPv2-TC:TruthValue;
          tailf:snmp-oid "1.3.6.1.2.1.4.39.1.6";
          default "false";
        }
        leaf ipv6RouterAdvertLinkMTU {
          type uint32;
          tailf:snmp-oid "1.3.6.1.2.1.4.39.1.7";
          default "0";
        }
        leaf ipv6RouterAdvertReachableTime {
          type ipv6RouterAdvertReachableTimeType;
          tailf:snmp-oid "1.3.6.1.2.1.4.39.1.8";
          default "0";
        }
        leaf ipv6RouterAdvertRetransmitTime {
          type uint32;
          tailf:snmp-oid "1.3.6.1.2.1.4.39.1.9";
          default "0";
        }
        leaf ipv6RouterAdvertCurHopLimit {
          type ipv6RouterAdvertCurHopLimitType;
          tailf:snmp-oid "1.3.6.1.2.1.4.39.1.10";
        }
        leaf ipv6RouterAdvertDefaultLifetime {
          type ipv6RouterAdvertDefaultLifetimeType;
          tailf:snmp-oid "1.3.6.1.2.1.4.39.1.11";
        }
      }
    }
    container icmpStatsTable {
      config false;
      list icmpStatsEntry {
        key "icmpStatsIPVersion";
        tailf:sort-order "snmp";
        config false;
        tailf:snmp-oid "1.3.6.1.2.1.5.29";
        leaf icmpStatsIPVersion {
          type INET-ADDRESS-MIB:InetVersion;
          tailf:snmp-oid "1.3.6.1.2.1.5.29.1.1";
        }
        leaf icmpStatsInMsgs {
          type yang:counter32;
          tailf:snmp-oid "1.3.6.1.2.1.5.29.1.2";
          config false;
        }
        leaf icmpStatsInErrors {
          type yang:counter32;
          tailf:snmp-oid "1.3.6.1.2.1.5.29.1.3";
          config false;
        }
        leaf icmpStatsOutMsgs {
          type yang:counter32;
          tailf:snmp-oid "1.3.6.1.2.1.5.29.1.4";
          config false;
        }
        leaf icmpStatsOutErrors {
          type yang:counter32;
          tailf:snmp-oid "1.3.6.1.2.1.5.29.1.5";
          config false;
        }
      }
    }
    container icmpMsgStatsTable {
      config false;
      list icmpMsgStatsEntry {
        key "icmpMsgStatsIPVersion icmpMsgStatsType";
        tailf:sort-order "snmp";
        config false;
        tailf:snmp-oid "1.3.6.1.2.1.5.30";
        leaf icmpMsgStatsIPVersion {
          type INET-ADDRESS-MIB:InetVersion;
          tailf:snmp-oid "1.3.6.1.2.1.5.30.1.1";
        }
        leaf icmpMsgStatsType {
          type icmpMsgStatsTypeType;
          tailf:snmp-oid "1.3.6.1.2.1.5.30.1.2";
        }
        leaf icmpMsgStatsInPkts {
          type yang:counter32;
          tailf:snmp-oid "1.3.6.1.2.1.5.30.1.3";
          config false;
        }
        leaf icmpMsgStatsOutPkts {
          type yang:counter32;
          tailf:snmp-oid "1.3.6.1.2.1.5.30.1.4";
          config false;
        }
      }
    }
  }
  typedef IpAddressOriginTC {
    type enumeration {
      enum "other" {
        value 1;
      }
      enum "manual" {
        value 2;
      }
      enum "dhcp" {
        value 4;
      }
      enum "linklayer" {
        value 5;
      }
      enum "random" {
        value 6;
      }
    }
  }
  typedef IpAddressStatusTC {
    type enumeration {
      enum "preferred" {
        value 1;
      }
      enum "deprecated" {
        value 2;
      }
      enum "invalid" {
        value 3;
      }
      enum "inaccessible" {
        value 4;
      }
      enum "unknown" {
        value 5;
      }
      enum "tentative" {
        value 6;
      }
      enum "duplicate" {
        value 7;
      }
      enum "optimistic" {
        value 8;
      }
    }
  }
  typedef IpAddressPrefixOriginTC {
    type enumeration {
      enum "other" {
        value 1;
      }
      enum "manual" {
        value 2;
      }
      enum "wellknown" {
        value 3;
      }
      enum "dhcp" {
        value 4;
      }
      enum "routeradv" {
        value 5;
      }
    }
  }
  typedef Ipv6AddressIfIdentifierTC {
    type tailf:hex-list {
      tailf:value-length "min .. 8";
    }
  }
  typedef ipForwardingType {
    type enumeration {
      enum "forwarding" {
        value 1;
      }
      enum "notForwarding" {
        value 2;
      }
    }
  }
  typedef ipDefaultTTLType {
    type int32 {
      range "1 .. 255";
    }
  }
  typedef ipv6IpForwardingType {
    type enumeration {
      enum "forwarding" {
        value 1;
      }
      enum "notForwarding" {
        value 2;
      }
    }
  }
  typedef ipv6IpDefaultHopLimitType {
    type int32 {
      range "0 .. 255";
    }
  }
  typedef ipAdEntIfIndexType {
    type int32 {
      range "1 .. 2147483647";
    }
  }
  typedef ipAdEntBcastAddrType {
    type int32 {
      range "0 .. 1";
    }
  }
  typedef ipAdEntReasmMaxSizeType {
    type int32 {
      range "0 .. 65535";
    }
  }
  typedef ipNetToMediaIfIndexType {
    type int32 {
      range "1 .. 2147483647";
    }
  }
  typedef ipNetToMediaPhysAddressType {
    type tailf:hex-list {
      tailf:value-length "min .. 65535";
    }
  }
  typedef ipNetToMediaTypeType {
    type enumeration {
      enum "other" {
        value 1;
      }
      enum "invalid" {
        value 2;
      }
      enum "dynamic" {
        value 3;
      }
      enum "static" {
        value 4;
      }
    }
  }
  typedef ipv4InterfaceReasmMaxSizeType {
    type int32 {
      range "0 .. 65535";
    }
  }
  typedef ipv4InterfaceEnableStatusType {
    type enumeration {
      enum "up" {
        value 1;
      }
      enum "down" {
        value 2;
      }
    }
  }
  typedef ipv6InterfaceReasmMaxSizeType {
    type uint32 {
      range "1500 .. 65535";
    }
  }
  typedef ipv6InterfaceEnableStatusType {
    type enumeration {
      enum "up" {
        value 1;
      }
      enum "down" {
        value 2;
      }
    }
  }
  typedef ipv6InterfaceForwardingType {
    type enumeration {
      enum "forwarding" {
        value 1;
      }
      enum "notForwarding" {
        value 2;
      }
    }
  }
  typedef ipAddressTypeType {
    type enumeration {
      enum "unicast" {
        value 1;
      }
      enum "anycast" {
        value 2;
      }
      enum "broadcast" {
        value 3;
      }
    }
  }
  typedef ipNetToPhysicalPhysAddressType {
    type tailf:hex-list {
      tailf:value-length "min .. 65535";
    }
  }
  typedef ipNetToPhysicalTypeType {
    type enumeration {
      enum "other" {
        value 1;
      }
      enum "invalid" {
        value 2;
      }
      enum "dynamic" {
        value 3;
      }
      enum "static" {
        value 4;
      }
      enum "local" {
        value 5;
      }
    }
  }
  typedef ipNetToPhysicalStateType {
    type enumeration {
      enum "reachable" {
        value 1;
      }
      enum "stale" {
        value 2;
      }
      enum "delay" {
        value 3;
      }
      enum "probe" {
        value 4;
      }
      enum "invalid" {
        value 5;
      }
      enum "unknown" {
        value 6;
      }
      enum "incomplete" {
        value 7;
      }
    }
  }
  typedef ipDefaultRouterLifetimeType {
    type uint32 {
      range "0 .. 65535";
    }
  }
  typedef ipDefaultRouterPreferenceType {
    type enumeration {
      enum "reserved" {
        value -2;
      }
      enum "low" {
        value -1;
      }
      enum "medium" {
        value 0;
      }
      enum "high" {
        value 1;
      }
    }
  }
  typedef ipv6RouterAdvertMaxIntervalType {
    type uint32 {
      range "4 .. 1800";
    }
  }
  typedef ipv6RouterAdvertMinIntervalType {
    type uint32 {
      range "3 .. 1350";
    }
  }
  typedef ipv6RouterAdvertReachableTimeType {
    type uint32 {
      range "0 .. 3600000";
    }
  }
  typedef ipv6RouterAdvertCurHopLimitType {
    type uint32 {
      range "0 .. 255";
    }
  }
  typedef ipv6RouterAdvertDefaultLifetimeType {
    type uint32 {
      range "0 .. 9000";
    }
  }
  typedef icmpMsgStatsTypeType {
    type int32 {
      range "0 .. 255";
    }
  }
}
