module INET-ADDRESS-MIB {
  namespace "http://tail-f.com/ns/mibs/INET-ADDRESS-MIB/200502040000Z";
  prefix INET_ADDRESS_MIB;
  tailf:id "";
  tailf:snmp-mib-module-name "INET-ADDRESS-MIB";
  import tailf-common {
    prefix tailf;
  }
  revision 2005-02-04 {
    description
      "";
  }
  typedef InetAddressType {
    type enumeration {
      enum "unknown" {
        value 0;
      }
      enum "ipv4" {
        value 1;
      }
      enum "ipv6" {
        value 2;
      }
      enum "ipv4z" {
        value 3;
      }
      enum "ipv6z" {
        value 4;
      }
      enum "dns" {
        value 16;
      }
    }
  }
  typedef InetAddress {
    type tailf:hex-list {
      tailf:value-length "min .. 255";
    }
  }
  typedef InetAddressIPv4 {
    type tailf:hex-list {
      tailf:value-length "4";
    }
  }
  typedef InetAddressIPv6 {
    type tailf:hex-list {
      tailf:value-length "16";
    }
  }
  typedef InetAddressIPv4z {
    type tailf:hex-list {
      tailf:value-length "8";
    }
  }
  typedef InetAddressIPv6z {
    type tailf:hex-list {
      tailf:value-length "20";
    }
  }
  typedef InetAddressDNS {
    type string {
      length "1 .. 255";
    }
  }
  typedef InetAddressPrefixLength {
    type uint32 {
      range "0 .. 2040";
    }
  }
  typedef InetPortNumber {
    type uint32 {
      range "0 .. 65535";
    }
  }
  typedef InetAutonomousSystemNumber {
    type uint32 {
      range "0 .. 4294967295";
    }
  }
  typedef InetScopeType {
    type enumeration {
      enum "interfaceLocal" {
        value 1;
      }
      enum "linkLocal" {
        value 2;
      }
      enum "subnetLocal" {
        value 3;
      }
      enum "adminLocal" {
        value 4;
      }
      enum "siteLocal" {
        value 5;
      }
      enum "organizationLocal" {
        value 8;
      }
      enum "global" {
        value 14;
      }
    }
  }
  typedef InetZoneIndex {
    type uint32 {
      range "0 .. 4294967295";
    }
  }
  typedef InetVersion {
    type enumeration {
      enum "unknown" {
        value 0;
      }
      enum "ipv4" {
        value 1;
      }
      enum "ipv6" {
        value 2;
      }
    }
  }
}
