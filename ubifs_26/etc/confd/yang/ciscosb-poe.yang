module ciscosb-poe {
    namespace "http://cisco.com/ns/ciscosb/poe";
    prefix ciscosb-poe;
    import ietf-interfaces { prefix if; }
    import iana-if-type { prefix ianaift; }
    import ciscosb-types { prefix ciscosb-types; }
    organization "Cisco Systems, Inc.";
    contact
        " Cisco Systems, Inc. Tel: +86 2124073170 E-mail:ciscosb-yang@cisco.com";
    description
        "This module enhance ietf-interfaces to add some rpc and statistics";
    revision 2016-06-01 {
        description "Add revision ";
        reference "";
    }
    revision 2015-05-23 {
        description
            "Fix type of /poe-state/operation-status.";
        reference "";
    }
    revision 2015-04-15 {
        description
            "Initial revision.";
        reference "TODO";
    }
    container global-poe-setting{
        leaf legacy{
            type boolean;
        }
        leaf snmp-trap-enable{
            type boolean;
        }
        leaf power-mode{
            type ciscosb-types:poe-power-mode;
        }
        leaf power-trap-thread{
            type int16{
                range 1..99;
            }
            default 95;
        }
    }
    container poe-state {
        config false;
        leaf operation-status{
            type enumeration{
                enum normal;
                enum fault;
            }
        }
        leaf nominal-power{
            type int16;
            units "w";
        }
        leaf consumed-power{
            type int16;
            units "w";
        }
        leaf allocated-power{
            type int16;
            units "w";
        }
        leaf available-power{
            type int16;
            units "w";
        }
    }
    augment "/if:interfaces/if:interface" {
        when "if:type = 'ianaift:ethernetCsmacd'"{
    }
    container poe-setting{
        leaf enable{
            type boolean;
        }
        choice poe-model{
            case class-limit{
                leaf class-limit{
                    type empty;
                }
            }
            case port-limit{
                leaf administration-power-allocation{
                    type int32{
                        range 0..30000;
                    }
                    units "mw";
                    default 30000;
                }
            }
        }
        leaf priority-level{
            type enumeration {
                enum low;
                enum high;
                enum critical;
            }
        }
    }
    }
    augment "/if:interfaces-state/if:interface" {
        when "if:type = 'ianaift:ethernetCsmacd'"{
    }
    container poe-state{
        choice poe-model{
            case port-limit{
                leaf administration-power-allocation{
                    type int32{
                        range 0..30000;
                    }
                    units "mw";
                    default 30000;
                }
            }
        }
        leaf class{
            type int8;
            config false;
        }
        leaf max-power{
            type int32;
            units "mw";
        }
        leaf consumed-power{
            type int32;
            units "mw";
        }
        leaf overload-counter{
            type int32;
        }
        leaf absent-counter{
            type int32;
        }
        leaf short-counter{
            type int32;
        }
        leaf denied-counter{
            type int32;
        }
        leaf invalid-signature-counter{
            type int32;
        }
        leaf poe-standard {
            type string;
        }
    }
    }
}
