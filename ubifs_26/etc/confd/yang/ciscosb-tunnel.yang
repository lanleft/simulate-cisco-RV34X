module ciscosb-tunnel {
    namespace "http://cisco.com/ns/ciscosb/tunnel";
    prefix "tunnel";
    import ietf-inet-types { prefix inet;}
    import ietf-interfaces {
        prefix if;
    }
    organization
        "Cisco Systems, Inc.";
    contact
        " Cisco Systems, Inc. Customer Service Postal: 170 W Tasman Drive
        San Jose, CA 95134 Tel: +1 1800 553-NETS E-mail: cs-yang@cisco.com";
    description
        "This module defines tunnel yang data model.";
    revision 2017-05-03 {
        description
            "Initial revision.";
    }
    identity technology-types {
        description
            "this is the base identity of technology types which are
            IP, GRE, MPLS, etc";
    }
    identity ipv4 {
        base technology-types;
        description
            "technology of ipv4";
    }
    identity ipv6 {
        base technology-types;
        description
            "technology of ipv6";
    }
    identity encapsulation-type{
        description
            "The encapsulation method used by a tunnel
            which are direct, GRE, 6to4, 6over4, IPsec, etc.";
    }
    identity direct{
        base encapsulation-type;
        description
            "no intermediate header.";
    }
    identity gre{
        base encapsulation-type;
        description
            "intermediate header is gre.";
    }
    identity endpoint-type{
        description
            "this is the base identity of tunnel type which are CE, PE, etc.";
    }
    augment "/if:interfaces/if:interface" {
        when "if:type = 'ianaift:tunnel'";
        description
            "Parameters for configuring tunnel on interfaces.";
        container tunnel-configuration{
            description
                "tunnel configuration model.";
            leaf base-interface {
                type if:interface-ref;
                must "/if:interfaces/if:interface[if:name = current()]" {
                    description
                        "The base interface.";
                }
                description
                    "The base interface.";
            }
            leaf technology{
                type identityref{
                    base technology-types;
                }
                description
                    "this leaf can be used to indicate different technologies
                    such as IP, GRE, MPLS, etc";
            }
            leaf encapsulation-method{
                type identityref{
                    base encapsulation-type;
                }
                description
                    "The encapsulation method used by a tunnel.";
            }
            leaf endpoint-type{
                type identityref{
                    base endpoint-type;
                }
                description
                    "The endpoint type.";
            }
            choice signaling-protocol-type {
                case signaling-protocol-null {
                    description
                        "this is a placeholder when no signaling protocol
                        is needed";
                    leaf signaling-null {
                        type empty;
                        description
                            "there is no signaling protocol define,
                            it will be defined in
                                technology specific model.";
                    }
                }
                description
                    "signaling protocol type";
            }
            container tunnel-source{
                description
                    "parameters of source tunnel";
                choice tunnel-source {
                    case interface{
                        leaf interface-type{
                            type leafref{
                                path "/if:interfaces/if:interface"
                                    +"/if:type";
                            }
                            description
                                "interface type";
                        }
                        leaf interface{
                            type if:interface-ref;
                            description
                                "Interface";
                        }
                    }
                    case ipv4-address {
                        leaf ipv4-address {
                            type inet:ipv4-address;
                            description
                                "Ipv4 Address";
                        }
                        description
                            "Ip Address based node Addressing.";
                    }
                    case ipv6-address {
                        leaf ipv6-address {
                            type inet:ipv6-address;
                            description
                                "Ipv6 Address";
                        }
                        description
                            "ipv6 Address based node Addressing.";
                    }
                    description
                        "node Addressing.";
                }
            }
            container tunnel-destination{
                description
                    "Data nodes for the operational state of tunnel on interfaces";
                choice tunnel-destination {
                    case interface{
                        leaf interface-type{
                            type leafref{
                                path "/if:interfaces/if:interface"
                                    +"/if:type";
                            }
                            description
                                "interface type";
                        }
                        leaf interface{
                            type if:interface-ref;
                            description
                                "Interface";
                        }
                    }
                    case ipv4-address {
                        leaf ipv4-address {
                            type inet:ipv4-address;
                            description
                                "Ipv4 Address";
                        }
                        description
                            "Ip Address based node Addressing.";
                    }
                    case ipv6-address {
                        leaf ipv6-address {
                            type inet:ipv6-address;
                            description
                                "Ipv6 Address";
                        }
                        description
                            "ipv6 Address based node Addressing.";
                    }
                    description
                        "node Addressing.";
                }
            }
            leaf ttl {
                type uint8;
                default "255";
                description
                    "Time to Live";
            }
            leaf priority {
                type uint8;
                description
                    "priority";
            }
            choice Multiplexing{
                description
                    "multiplexing parameters";
                case multiplexing-null{
                    description
                        "this is a placeholder when no multiplexing is needed";
                    leaf multiplexing-null{
                        type empty;
                        description
                            "there is no multiplexing define, it will be defined
                            in technology specific model.";
                    }
                }
            }
            choice QoS{
                description
                    "QoS Parameters";
                case Qos-null{
                    description
                        "this is a placeholder when no QoS is needed";
                    leaf QoS-null{
                        type empty;
                        description
                            "there is no QoS define, it will be defined
                            in technology specific model.";
                    }
                }
            }
            choice Security{
                description
                    "security parameters";
                case Security-null{
                    description
                        "this is a placeholder when no Security is needed";
                    leaf Security-null{
                        type empty;
                        description
                            "there is no Security define, it will be defined
                            in technology specific model.";
                    }
                }
            }
            container resource{
                description
                    "this container is used to indicate the resources required
                    for a tunnel.";
                leaf bandwidth{
                    type uint32;
                    description
                        "the bandwidth of tunnel";
                }
                leaf MaxRate{
                    type uint32;
                    description
                        "The maximum rate in bits/second.";
                }
                leaf MaxBurstSize{
                    type uint32;
                    description
                        "The maximum burst size in bytes.";
                }
                leaf ExBurstSize{
                    type uint32;
                    description
                        "The Excess burst size in bytes.";
                }
                leaf Frequency{
                    type uint32;
                    description
                        "The granularity of the availability of committed
                        rate.";
                }
                leaf weight{
                    type uint32;
                    description
                        "The relative weight for using excess bandwidth above
                        its committed rate.";
                }
            }
        }
    }
}
