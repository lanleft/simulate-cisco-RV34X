module ietf-syslog {
  namespace "urn:ietf:params:xml:ns:yang:ietf-syslog";
  prefix syslog;

  import ietf-inet-types {
    prefix inet;
  }

  import ietf-interfaces {
    prefix if;
  }

  import ietf-syslog-types {
    prefix syslogtypes;
  }

  organization "IETF NETMOD (NETCONF Data Modeling Language) 
  Working Group";
  contact
    "WG Web:   <http://tools.ietf.org/wg/netmod/>
     WG List:  <mailto:netmod@ietf.org>
     
     WG Chair: David Kessens
               <mailto:david.kessens@nsn.com>
     
     WG Chair: Juergen Schoenwaelder
               <mailto:j.schoenwaelder@jacobs-university.de>
     
     Editor:   Ladislav Lhotka
               <mailto:lhotka@nic.cz>";
  description
    "This module contains a collection of YANG definitions 
     for Syslog configuration.";

  revision 2014-10-24 {
    description
      "syslog-model-04 Revision";
    reference
      "This model references RFC 5424 - The Syslog Protocol, 
       and RFC 5848 - Signed Syslog Messages.";
  }

  feature global-logging-action {
    description
      "This feature represents the ability to suppress log
       messages on the global level.";
  }

  feature file-logging-structured-data {
    description
      "This feature represents the ability to log messages 
       to a file in structured-data format as per RFC 5424.";
  }

  feature file-logging-archive-config {
    description
      "This feature represents the ability to archive log files.";
  }

  feature remote-logging-use-vrf {
    description
      "This feature allows remote logging of messages to a 
       particular VRF.";
  }

  feature terminal-facility-user-logging-config {
    description
      "This feature represents the ability to adjust 
       log message settings for individual terminal users.";
  }

  feature selector-advanced-level-processing-config {
    description
      "This feature represents the ability to select messages 
       using the additional operators equal to, or not equal to 
       when comparing the Syslog message severity.";
  }

  feature selector-match-processing-config {
    description
      "This feature represents the ability to select messages based
       on a Posix 1003.2 regular expression pattern match.";
  }

  feature signed-messages-config {
    description
      "This feature represents the ability to configure signed 
       syslog messages according to RFC 5848.";
  }

  grouping syslog-severity {
    description
      "This grouping defines the Syslog severity which is used to 
       filter log messages. Choose one of the following:
         logging-severity-all 
         logging-severity <severity>";
    choice logging-severity-scope {
      description
        "This choice describes the option to specify all severities 
         or a specific severity.";
      case logging-severity-all {
        description
          "This case specifies all severities.";
        leaf all {
          type empty;
          description
          "This leaf specifies that all severities participate in 
           the filtering of Syslog messages.";
        }
      }
      case logging-severity {
        description
          "This case specifies a specific severity to participate 
           in the filtering of Syslog messages.";
        leaf severity {
          type syslogtypes:Severity;
          description
            "This leaf specifies the Syslog message severity.";
        }
      }
    }
  }

  grouping syslog-selector {
    description
      "This grouping defines a Syslog selector which is used to 
       filter log messages for the given action in which the 
       selector appears. Choose one of the following:
         logging-facility-all <severity> 
         logging-facility-none
         logging-facility [<facility> <severity>...]
       Additional severity comparison operations are available 
       using the logging-advanced-level-processing container. If
       the logging-advanced-level-processing container is not 
       present all messages of the specified severity and higher 
       are logged according to the given action.";
    choice logging-level-scope {
      description
        "This choice describes the option to specify all 
         facilities, no facilities, or a specific facility.";
      case logging-facility-all {
        description
          "This case specifies all facilities will match when 
           comparing the Syslog message facility.";
        uses syslog-severity;
      }
      case logging-facility-none {
        description
          "This case specifies no facilities will match when 
           comparing the Syslog message facility. This is a method 
           that can be used to turn an action off.";
        leaf none {
          type empty;
          description
          "This leaf specifies that no facilities participate in the 
           filtering of Syslog messages for this action.";
        }
      }
      case logging-facility {
        description
          "This case specifies one or more specified facilities 
           will match when comparing the Syslog message facility.";
        list logging-facilities {
          key "facility";
          description
            "This list describes a collection of Syslog facilities 
             and severities.";
          leaf facility {
            type identityref {
              base syslogtypes:syslog-facility;
            }
            description
              "The leaf uniquely identifies a Syslog facility.";
          }
          uses syslog-severity;
        }
      }
    }
    container logging-advanced-level-processing {
      if-feature selector-advanced-level-processing-config;
      description
        "This container describes the configuration parameters for 
         advanced Syslog selector severity comparison.";
      choice logging-severity-operator {
        description
          "This choice describes the option to specify how the 
           severity comparison is performed.";    
        case default {
          description
            "All messages of the specified severity and higher are 
             logged according to the given action";
          leaf default {
            type empty;
            description
            "This leaf specifies the default behavior.";
          }
        }
        case equals {
          description
            "All messages of the specified severity are logged 
             according to the given action";
          leaf equals {
            type empty;
            description
            "This leaf specifies all messages for the specified 
             severity.";
          }
        }
        case not-equals {
          description
            "All messages that are not of the specified severity are 
             logged according to the given action";
          leaf not-equals {
            type empty;
            description
            "This leaf specifies all messages that are not for the 
             specified severity.";
          }
        }
      }
    }
    container logging-match-processing {
      if-feature selector-match-processing-config;
      description
        "This container describes the configuration parameters for 
         matching Syslog messages using a regular expression pattern 
         match.";
      leaf pattern-match {
        type string;
        description
          "This leaf desribes a Posix 1003.2 regular expression 
           string that can be used to select a Syslog message for 
           logging.";
      }
    }
  }

  container syslog {
    config true;
    description
      "This container describes the configuration parameters for 
       Syslog.";
    container global-logging-action {
      if-feature global-logging-action;
      description
        "This container describes the configuration parameters for 
         global logging. Global logging represents the ability to 
         perform global log message suppression.";
      uses syslog-selector;
    }
    container console-logging-action {
      description
        "This container describes the configuration parameters for 
         console logging.";
      uses syslog-selector;
    }
    container file-logging-action {
      description
        "This container describes the configuration parameters for 
         file logging.";
      leaf file-name {
        type inet:uri;
        //mandatory true;
        description
          "This leaf specifies the name of the log file.";
      }
      uses syslog-selector;
      leaf file-logging-structured-data {
        if-feature file-logging-structured-data;
        type boolean;
        description
          "This leaf describes how log messages are written to the 
           log file. If set messages will be written in structured-
           data format; if not set messages will be written in 
           standard message format.";
      }
      container file-logging-archive {
        if-feature file-logging-archive-config;
        description
          "This container describes the configuration parameters for 
           log file archiving.";
        leaf file-number {
          type uint32;
          description
            "This leaf specifies the maximum number of log files 
             retained.";
        }
        leaf file-size {
          type uint32;
          description
            "This leaf specifies the maximum log file size.";
        }
        leaf file-permission {
          type enumeration {
             enum world-readable {
               value 1;
               description
                 "This enum specifies that the log files 
                  are readable by world.";
             }
             enum no-world-readable {
               value 2;
               description
                 "This enum specifies that the log files 
                  are not readable by world.";
             }
          }
          description
            "This leaf describes who can read log files";
        }
      }
    }
    container remote-logging-action {
      description
        "This container describes the configuration parameters for 
         remote logging.";
      list remote-logging-destination {
        key "destination";
        description
          "This list describes a collection of remote logging 
           destinations.";
        leaf destination {
          type inet:host;
          mandatory true;
          description
            "The leaf uniquely specifies the address of the 
             remote host. One of the following must be specified: 
             an ipv4 address, an ipv6 address, or a host name.";
        }
        uses syslog-selector;
        leaf destination-facility {
          type identityref {
            base syslogtypes:syslog-facility;
          }
          description
            "This leaf specifies the facility used in messages 
             delivered to the remote server.";
        }
        leaf source-interface {
          type if:interface-ref;
          description
            "This leaf sets the source interface for the remote 
             Syslog server. Either the interface name or the 
             interface IP address can be specified.";
        }
        leaf vrf-name {
          if-feature remote-logging-use-vrf;
          type string;
          description
            "This leaf specifies the name of the virtual routing 
             facility (VRF).";
        }
        container syslog-sign {
          if-feature signed-messages-config;
          presence
            "If present, syslog-sign is activated.";
          description
            "This container describes the configuration parameters 
             for signed syslog messages as described by RFC 5848.";
          leaf certInitialRepeat {
            type uint16;
            description
            "This leaf specifies the number of times each 
             Certificate Block should be sent before the first 
             message is sent.";
          }
          leaf certResendDelay {
            type uint16;
            description
              "This leaf specifies the maximum time delay in seconds 
               until resending the Certificate Block.";
          }
          leaf certResendCount {
            type uint16;
            description
              "This leaf specifies the maximum number of other 
               syslog messages to send until resending the 
               Certificate Block.";
          }
          leaf sigMaxDelay {
            type uint16;
            description
              "This leaf specifies when to generate a new Signature 
               Block. If this many seconds have elapsed since the 
               message with the first message number of the 
               Signature Block was sent, a new Signature Block 
               should be generated.";
          }
          leaf sigNumberResends {
            type uint16;
            description
              "This leaf specifies the number of times a Signature 
               Block is resent. (It is recommended to select a value 
               of greater than 0 in particular when the UDP 
               transport [RFC5426] is used.).";
          }
          leaf sigResendDelay {
            type uint16;
            description
              "This leaf specifies when to send the next Signature 
               Block transmission based on time. If this many 
               seconds have elapsed since the previous sending of 
               this Signature Block, resend it.";
          }
          leaf sigResendCount {
            type uint16;
            description
              "This leaf specifies when to send the next Signature 
               Block transmission based on a count. If this many 
               other syslog messages have been sent since the 
               previous sending of this Signature Block, resend it.";
          }
        }
      }
    }
    container terminal-logging-action {
      description
        "This container describes the configuration parameters for 
         the terminal logging configuration.";
      choice user-scope {
        description
          "This choice describes the option to specify all users 
           or a specific user. The all users case implies that
           messages will be sent to all terminals";
        case all-users {
          description
            "This case specifies all users.";
          container all-users {
            description
              "This container describes the configuration parameters 
               for all users.";
            uses syslog-selector;
          }
        }
        case per-user {
          if-feature terminal-facility-user-logging-config;
          description
            "This case specifies a specific user.";
          list user-name {
            key "uname";
            description
              "This list describes a collection of user names.";
            leaf uname {
              type string;
              description
                "This leaf uniquely describes a user name.";
            }
            uses syslog-selector;
          }
        }
      }
    }
  }
}
