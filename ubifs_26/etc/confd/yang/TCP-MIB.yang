module TCP-MIB {
  namespace "http://tail-f.com/ns/mibs/TCP-MIB/200502180000Z";
  prefix TCP_MIB;
  tailf:id "";
  tailf:snmp-mib-module-name "TCP-MIB";
  import ietf-yang-types {
    prefix yang;
  }
  import ietf-inet-types {
    prefix inet;
  }
  import tailf-common {
    prefix tailf;
  }
  import INET-ADDRESS-MIB {
    prefix INET-ADDRESS-MIB;
  }
  revision 2005-02-18 {
    description
      "";
  }
  container TCP-MIB {
    container tcp {
      tailf:snmp-oid "1.3.6.1.2.1.6";
      leaf tcpRtoAlgorithm {
        type tcpRtoAlgorithmType;
        tailf:snmp-oid "1.3.6.1.2.1.6.1";
        config false;
      }
      leaf tcpRtoMin {
        type tcpRtoMinType;
        tailf:snmp-oid "1.3.6.1.2.1.6.2";
        config false;
      }
      leaf tcpRtoMax {
        type tcpRtoMaxType;
        tailf:snmp-oid "1.3.6.1.2.1.6.3";
        config false;
      }
      leaf tcpMaxConn {
        type tcpMaxConnType;
        tailf:snmp-oid "1.3.6.1.2.1.6.4";
        config false;
      }
      leaf tcpActiveOpens {
        type yang:counter32;
        tailf:snmp-oid "1.3.6.1.2.1.6.5";
        config false;
      }
      leaf tcpPassiveOpens {
        type yang:counter32;
        tailf:snmp-oid "1.3.6.1.2.1.6.6";
        config false;
      }
      leaf tcpAttemptFails {
        type yang:counter32;
        tailf:snmp-oid "1.3.6.1.2.1.6.7";
        config false;
      }
      leaf tcpEstabResets {
        type yang:counter32;
        tailf:snmp-oid "1.3.6.1.2.1.6.8";
        config false;
      }
      leaf tcpCurrEstab {
        type yang:gauge32;
        tailf:snmp-oid "1.3.6.1.2.1.6.9";
        config false;
      }
      leaf tcpInSegs {
        type yang:counter32;
        tailf:snmp-oid "1.3.6.1.2.1.6.10";
        config false;
      }
      leaf tcpOutSegs {
        type yang:counter32;
        tailf:snmp-oid "1.3.6.1.2.1.6.11";
        config false;
      }
      leaf tcpRetransSegs {
        type yang:counter32;
        tailf:snmp-oid "1.3.6.1.2.1.6.12";
        config false;
      }
      leaf tcpInErrs {
        type yang:counter32;
        tailf:snmp-oid "1.3.6.1.2.1.6.14";
        config false;
      }
      leaf tcpOutRsts {
        type yang:counter32;
        tailf:snmp-oid "1.3.6.1.2.1.6.15";
        config false;
      }
      leaf tcpHCInSegs {
        type yang:counter64;
        tailf:snmp-oid "1.3.6.1.2.1.6.17";
        config false;
      }
      leaf tcpHCOutSegs {
        type yang:counter64;
        tailf:snmp-oid "1.3.6.1.2.1.6.18";
        config false;
      }
    }
    container tcpConnTable {
      list tcpConnEntry {
        key "tcpConnLocalAddress tcpConnLocalPort tcpConnRemAddress tcpConnRemPort";
        tailf:sort-order "snmp";
        tailf:snmp-oid "1.3.6.1.2.1.6.13";
        leaf tcpConnLocalAddress {
          type inet:ipv4-address;
          tailf:snmp-oid "1.3.6.1.2.1.6.13.1.2";
        }
        leaf tcpConnLocalPort {
          type tcpConnLocalPortType;
          tailf:snmp-oid "1.3.6.1.2.1.6.13.1.3";
        }
        leaf tcpConnRemAddress {
          type inet:ipv4-address;
          tailf:snmp-oid "1.3.6.1.2.1.6.13.1.4";
        }
        leaf tcpConnRemPort {
          type tcpConnRemPortType;
          tailf:snmp-oid "1.3.6.1.2.1.6.13.1.5";
        }
        leaf tcpConnState {
          type tcpConnStateType;
          tailf:snmp-oid "1.3.6.1.2.1.6.13.1.1";
        }
      }
    }
    container tcpConnectionTable {
      list tcpConnectionEntry {
        key "tcpConnectionLocalAddressType tcpConnectionLocalAddress tcpConnectionLocalPort tcpConnectionRemAddressType tcpConnectionRemAddress tcpConnectionRemPort";
        tailf:sort-order "snmp";
        tailf:snmp-oid "1.3.6.1.2.1.6.19";
        leaf tcpConnectionLocalAddressType {
          type INET-ADDRESS-MIB:InetAddressType;
          tailf:snmp-oid "1.3.6.1.2.1.6.19.1.1";
        }
        leaf tcpConnectionLocalAddress {
          type INET-ADDRESS-MIB:InetAddress;
          tailf:snmp-oid "1.3.6.1.2.1.6.19.1.2";
        }
        leaf tcpConnectionLocalPort {
          type INET-ADDRESS-MIB:InetPortNumber;
          tailf:snmp-oid "1.3.6.1.2.1.6.19.1.3";
        }
        leaf tcpConnectionRemAddressType {
          type INET-ADDRESS-MIB:InetAddressType;
          tailf:snmp-oid "1.3.6.1.2.1.6.19.1.4";
        }
        leaf tcpConnectionRemAddress {
          type INET-ADDRESS-MIB:InetAddress;
          tailf:snmp-oid "1.3.6.1.2.1.6.19.1.5";
        }
        leaf tcpConnectionRemPort {
          type INET-ADDRESS-MIB:InetPortNumber;
          tailf:snmp-oid "1.3.6.1.2.1.6.19.1.6";
        }
        leaf tcpConnectionState {
          type tcpConnectionStateType;
          tailf:snmp-oid "1.3.6.1.2.1.6.19.1.7";
        }
        leaf tcpConnectionProcess {
          type uint32;
          tailf:snmp-oid "1.3.6.1.2.1.6.19.1.8";
          config false;
        }
      }
    }
    container tcpListenerTable {
      config false;
      list tcpListenerEntry {
        key "tcpListenerLocalAddressType tcpListenerLocalAddress tcpListenerLocalPort";
        tailf:sort-order "snmp";
        config false;
        tailf:snmp-oid "1.3.6.1.2.1.6.20";
        leaf tcpListenerLocalAddressType {
          type INET-ADDRESS-MIB:InetAddressType;
          tailf:snmp-oid "1.3.6.1.2.1.6.20.1.1";
        }
        leaf tcpListenerLocalAddress {
          type INET-ADDRESS-MIB:InetAddress;
          tailf:snmp-oid "1.3.6.1.2.1.6.20.1.2";
        }
        leaf tcpListenerLocalPort {
          type INET-ADDRESS-MIB:InetPortNumber;
          tailf:snmp-oid "1.3.6.1.2.1.6.20.1.3";
        }
        leaf tcpListenerProcess {
          type uint32;
          tailf:snmp-oid "1.3.6.1.2.1.6.20.1.4";
          config false;
        }
      }
    }
  }
  typedef tcpRtoAlgorithmType {
    type enumeration {
      enum "other" {
        value 1;
      }
      enum "constant" {
        value 2;
      }
      enum "rsre" {
        value 3;
      }
      enum "vanj" {
        value 4;
      }
      enum "rfc2988" {
        value 5;
      }
    }
  }
  typedef tcpRtoMinType {
    type int32 {
      range "0 .. 2147483647";
    }
  }
  typedef tcpRtoMaxType {
    type int32 {
      range "0 .. 2147483647";
    }
  }
  typedef tcpMaxConnType {
    type int32 {
      range "-1 .. 2147483647";
    }
  }
  typedef tcpConnLocalPortType {
    type int32 {
      range "0 .. 65535";
    }
  }
  typedef tcpConnRemPortType {
    type int32 {
      range "0 .. 65535";
    }
  }
  typedef tcpConnStateType {
    type enumeration {
      enum "closed" {
        value 1;
      }
      enum "listen" {
        value 2;
      }
      enum "synSent" {
        value 3;
      }
      enum "synReceived" {
        value 4;
      }
      enum "established" {
        value 5;
      }
      enum "finWait1" {
        value 6;
      }
      enum "finWait2" {
        value 7;
      }
      enum "closeWait" {
        value 8;
      }
      enum "lastAck" {
        value 9;
      }
      enum "closing" {
        value 10;
      }
      enum "timeWait" {
        value 11;
      }
      enum "deleteTCB" {
        value 12;
      }
    }
  }
  typedef tcpConnectionStateType {
    type enumeration {
      enum "closed" {
        value 1;
      }
      enum "listen" {
        value 2;
      }
      enum "synSent" {
        value 3;
      }
      enum "synReceived" {
        value 4;
      }
      enum "established" {
        value 5;
      }
      enum "finWait1" {
        value 6;
      }
      enum "finWait2" {
        value 7;
      }
      enum "closeWait" {
        value 8;
      }
      enum "lastAck" {
        value 9;
      }
      enum "closing" {
        value 10;
      }
      enum "timeWait" {
        value 11;
      }
      enum "deleteTCB" {
        value 12;
      }
    }
  }
}
