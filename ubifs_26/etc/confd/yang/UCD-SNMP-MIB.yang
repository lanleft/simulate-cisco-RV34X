module UCD-SNMP-MIB {
  namespace "http://tail-f.com/ns/mibs/UCD-SNMP-MIB/200101170000Z";
  prefix UCD_SNMP_MIB;
  tailf:id "";
  tailf:snmp-mib-module-name "UCD-SNMP-MIB";
  import ietf-yang-types {
    prefix yang;
  }
  import tailf-common {
    prefix tailf;
  }
  import SNMPv2-TC {
    prefix SNMPv2-TC;
  }
  revision 2001-01-17 {
    description
      "";
  }
  container UCD-SNMP-MIB {
    container memory {
      tailf:snmp-oid "1.3.6.1.4.1.2021.4";
      config false;
      leaf memIndex {
        type int32;
        tailf:snmp-oid "1.3.6.1.4.1.2021.4.1";
        config false;
      }
      leaf memErrorName {
        type string {
          length "0 .. 255";
        }
        tailf:snmp-oid "1.3.6.1.4.1.2021.4.2";
        config false;
      }
      leaf memTotalSwap {
        type int32;
        tailf:snmp-oid "1.3.6.1.4.1.2021.4.3";
        config false;
      }
      leaf memAvailSwap {
        type int32;
        tailf:snmp-oid "1.3.6.1.4.1.2021.4.4";
        config false;
      }
      leaf memTotalReal {
        type int32;
        tailf:snmp-oid "1.3.6.1.4.1.2021.4.5";
        config false;
      }
      leaf memAvailReal {
        type int32;
        tailf:snmp-oid "1.3.6.1.4.1.2021.4.6";
        config false;
      }
      leaf memTotalSwapTXT {
        type int32;
        tailf:snmp-oid "1.3.6.1.4.1.2021.4.7";
        config false;
      }
      leaf memAvailSwapTXT {
        type int32;
        tailf:snmp-oid "1.3.6.1.4.1.2021.4.8";
        config false;
      }
      leaf memTotalRealTXT {
        type int32;
        tailf:snmp-oid "1.3.6.1.4.1.2021.4.9";
        config false;
      }
      leaf memAvailRealTXT {
        type int32;
        tailf:snmp-oid "1.3.6.1.4.1.2021.4.10";
        config false;
      }
      leaf memTotalFree {
        type int32;
        tailf:snmp-oid "1.3.6.1.4.1.2021.4.11";
        config false;
      }
      leaf memMinimumSwap {
        type int32;
        tailf:snmp-oid "1.3.6.1.4.1.2021.4.12";
        config false;
      }
      leaf memShared {
        type int32;
        tailf:snmp-oid "1.3.6.1.4.1.2021.4.13";
        config false;
      }
      leaf memBuffer {
        type int32;
        tailf:snmp-oid "1.3.6.1.4.1.2021.4.14";
        config false;
      }
      leaf memCached {
        type int32;
        tailf:snmp-oid "1.3.6.1.4.1.2021.4.15";
        config false;
      }
      leaf memSwapError {
        type int32;
        tailf:snmp-oid "1.3.6.1.4.1.2021.4.100";
        config false;
      }
      leaf memSwapErrorMsg {
        type string {
          length "0 .. 255";
        }
        tailf:snmp-oid "1.3.6.1.4.1.2021.4.101";
        config false;
      }
    }
    container systemStats {
      tailf:snmp-oid "1.3.6.1.4.1.2021.11";
      config false;
      leaf ssIndex {
        type int32;
        tailf:snmp-oid "1.3.6.1.4.1.2021.11.1";
        config false;
      }
      leaf ssErrorName {
        type string {
          length "0 .. 255";
        }
        tailf:snmp-oid "1.3.6.1.4.1.2021.11.2";
        config false;
      }
      leaf ssSwapIn {
        type int32;
        tailf:snmp-oid "1.3.6.1.4.1.2021.11.3";
        config false;
      }
      leaf ssSwapOut {
        type int32;
        tailf:snmp-oid "1.3.6.1.4.1.2021.11.4";
        config false;
      }
      leaf ssIOSent {
        type int32;
        tailf:snmp-oid "1.3.6.1.4.1.2021.11.5";
        config false;
      }
      leaf ssIOReceive {
        type int32;
        tailf:snmp-oid "1.3.6.1.4.1.2021.11.6";
        config false;
      }
      leaf ssSysInterrupts {
        type int32;
        tailf:snmp-oid "1.3.6.1.4.1.2021.11.7";
        config false;
      }
      leaf ssSysContext {
        type int32;
        tailf:snmp-oid "1.3.6.1.4.1.2021.11.8";
        config false;
      }
      leaf ssCpuUser {
        type int32;
        tailf:snmp-oid "1.3.6.1.4.1.2021.11.9";
        config false;
      }
      leaf ssCpuSystem {
        type int32;
        tailf:snmp-oid "1.3.6.1.4.1.2021.11.10";
        config false;
      }
      leaf ssCpuIdle {
        type int32;
        tailf:snmp-oid "1.3.6.1.4.1.2021.11.11";
        config false;
      }
      leaf ssCpuRawUser {
        type yang:counter32;
        tailf:snmp-oid "1.3.6.1.4.1.2021.11.50";
        config false;
      }
      leaf ssCpuRawNice {
        type yang:counter32;
        tailf:snmp-oid "1.3.6.1.4.1.2021.11.51";
        config false;
      }
      leaf ssCpuRawSystem {
        type yang:counter32;
        tailf:snmp-oid "1.3.6.1.4.1.2021.11.52";
        config false;
      }
      leaf ssCpuRawIdle {
        type yang:counter32;
        tailf:snmp-oid "1.3.6.1.4.1.2021.11.53";
        config false;
      }
      leaf ssCpuRawWait {
        type yang:counter32;
        tailf:snmp-oid "1.3.6.1.4.1.2021.11.54";
        config false;
      }
      leaf ssCpuRawKernel {
        type yang:counter32;
        tailf:snmp-oid "1.3.6.1.4.1.2021.11.55";
        config false;
      }
      leaf ssCpuRawInterrupt {
        type yang:counter32;
        tailf:snmp-oid "1.3.6.1.4.1.2021.11.56";
        config false;
      }
      leaf ssIORawSent {
        type yang:counter32;
        tailf:snmp-oid "1.3.6.1.4.1.2021.11.57";
        config false;
      }
      leaf ssIORawReceived {
        type yang:counter32;
        tailf:snmp-oid "1.3.6.1.4.1.2021.11.58";
        config false;
      }
      leaf ssRawInterrupts {
        type yang:counter32;
        tailf:snmp-oid "1.3.6.1.4.1.2021.11.59";
        config false;
      }
      leaf ssRawContexts {
        type yang:counter32;
        tailf:snmp-oid "1.3.6.1.4.1.2021.11.60";
        config false;
      }
    }
    container version {
      tailf:snmp-oid "1.3.6.1.4.1.2021.100";
      leaf versionIndex {
        type int32;
        tailf:snmp-oid "1.3.6.1.4.1.2021.100.1";
        config false;
      }
      leaf versionTag {
        type string {
          length "0 .. 255";
        }
        tailf:snmp-oid "1.3.6.1.4.1.2021.100.2";
        config false;
      }
      leaf versionDate {
        type string {
          length "0 .. 255";
        }
        tailf:snmp-oid "1.3.6.1.4.1.2021.100.3";
        config false;
      }
      leaf versionCDate {
        type string {
          length "0 .. 255";
        }
        tailf:snmp-oid "1.3.6.1.4.1.2021.100.4";
        config false;
      }
      leaf versionIdent {
        type string {
          length "0 .. 255";
        }
        tailf:snmp-oid "1.3.6.1.4.1.2021.100.5";
        config false;
      }
      leaf versionConfigureOptions {
        type string {
          length "0 .. 255";
        }
        tailf:snmp-oid "1.3.6.1.4.1.2021.100.6";
        config false;
      }
      leaf versionClearCache {
        type int32;
        tailf:snmp-oid "1.3.6.1.4.1.2021.100.10";
      }
      leaf versionUpdateConfig {
        type int32;
        tailf:snmp-oid "1.3.6.1.4.1.2021.100.11";
      }
      leaf versionRestartAgent {
        type int32;
        tailf:snmp-oid "1.3.6.1.4.1.2021.100.12";
      }
      leaf versionDoDebugging {
        type int32;
        tailf:snmp-oid "1.3.6.1.4.1.2021.100.20";
      }
    }
    container snmperrs {
      tailf:snmp-oid "1.3.6.1.4.1.2021.101";
      config false;
      leaf snmperrIndex {
        type int32;
        tailf:snmp-oid "1.3.6.1.4.1.2021.101.1";
        config false;
      }
      leaf snmperrNames {
        type string {
          length "0 .. 255";
        }
        tailf:snmp-oid "1.3.6.1.4.1.2021.101.2";
        config false;
      }
      leaf snmperrErrorFlag {
        type int32;
        tailf:snmp-oid "1.3.6.1.4.1.2021.101.100";
        config false;
      }
      leaf snmperrErrMessage {
        type string {
          length "0 .. 255";
        }
        tailf:snmp-oid "1.3.6.1.4.1.2021.101.101";
        config false;
      }
    }
    container prTable {
      list prEntry {
        key "prIndex";
        tailf:sort-order "snmp";
        tailf:snmp-oid "1.3.6.1.4.1.2021.2";
        leaf prIndex {
          type prIndexType;
          tailf:snmp-oid "1.3.6.1.4.1.2021.2.1.1";
        }
        leaf prNames {
          type string {
            length "0 .. 255";
          }
          tailf:snmp-oid "1.3.6.1.4.1.2021.2.1.2";
          config false;
        }
        leaf prMin {
          type int32;
          tailf:snmp-oid "1.3.6.1.4.1.2021.2.1.3";
          config false;
        }
        leaf prMax {
          type int32;
          tailf:snmp-oid "1.3.6.1.4.1.2021.2.1.4";
          config false;
        }
        leaf prCount {
          type int32;
          tailf:snmp-oid "1.3.6.1.4.1.2021.2.1.5";
          config false;
        }
        leaf prErrorFlag {
          type int32;
          tailf:snmp-oid "1.3.6.1.4.1.2021.2.1.100";
          config false;
        }
        leaf prErrMessage {
          type string {
            length "0 .. 255";
          }
          tailf:snmp-oid "1.3.6.1.4.1.2021.2.1.101";
          config false;
        }
        leaf prErrFix {
          type int32;
          tailf:snmp-oid "1.3.6.1.4.1.2021.2.1.102";
        }
        leaf prErrFixCmd {
          type string {
            length "0 .. 255";
          }
          tailf:snmp-oid "1.3.6.1.4.1.2021.2.1.103";
          config false;
        }
      }
    }
    container extTable {
      list extEntry {
        key "extIndex";
        tailf:sort-order "snmp";
        tailf:snmp-oid "1.3.6.1.4.1.2021.8";
        leaf extIndex {
          type extIndexType;
          tailf:snmp-oid "1.3.6.1.4.1.2021.8.1.1";
        }
        leaf extNames {
          type string {
            length "0 .. 255";
          }
          tailf:snmp-oid "1.3.6.1.4.1.2021.8.1.2";
          config false;
        }
        leaf extCommand {
          type string {
            length "0 .. 255";
          }
          tailf:snmp-oid "1.3.6.1.4.1.2021.8.1.3";
          config false;
        }
        leaf extResult {
          type int32;
          tailf:snmp-oid "1.3.6.1.4.1.2021.8.1.100";
          config false;
        }
        leaf extOutput {
          type string {
            length "0 .. 255";
          }
          tailf:snmp-oid "1.3.6.1.4.1.2021.8.1.101";
          config false;
        }
        leaf extErrFix {
          type int32;
          tailf:snmp-oid "1.3.6.1.4.1.2021.8.1.102";
        }
        leaf extErrFixCmd {
          type string {
            length "0 .. 255";
          }
          tailf:snmp-oid "1.3.6.1.4.1.2021.8.1.103";
          config false;
        }
      }
    }
    container dskTable {
      config false;
      list dskEntry {
        key "dskIndex";
        tailf:sort-order "snmp";
        config false;
        tailf:snmp-oid "1.3.6.1.4.1.2021.9";
        leaf dskIndex {
          type dskIndexType;
          tailf:snmp-oid "1.3.6.1.4.1.2021.9.1.1";
        }
        leaf dskPath {
          type string {
            length "0 .. 255";
          }
          tailf:snmp-oid "1.3.6.1.4.1.2021.9.1.2";
          config false;
        }
        leaf dskDevice {
          type string {
            length "0 .. 255";
          }
          tailf:snmp-oid "1.3.6.1.4.1.2021.9.1.3";
          config false;
        }
        leaf dskMinimum {
          type int32;
          tailf:snmp-oid "1.3.6.1.4.1.2021.9.1.4";
          config false;
        }
        leaf dskMinPercent {
          type int32;
          tailf:snmp-oid "1.3.6.1.4.1.2021.9.1.5";
          config false;
        }
        leaf dskTotal {
          type int32;
          tailf:snmp-oid "1.3.6.1.4.1.2021.9.1.6";
          config false;
        }
        leaf dskAvail {
          type int32;
          tailf:snmp-oid "1.3.6.1.4.1.2021.9.1.7";
          config false;
        }
        leaf dskUsed {
          type int32;
          tailf:snmp-oid "1.3.6.1.4.1.2021.9.1.8";
          config false;
        }
        leaf dskPercent {
          type int32;
          tailf:snmp-oid "1.3.6.1.4.1.2021.9.1.9";
          config false;
        }
        leaf dskPercentNode {
          type int32;
          tailf:snmp-oid "1.3.6.1.4.1.2021.9.1.10";
          config false;
        }
        leaf dskErrorFlag {
          type int32;
          tailf:snmp-oid "1.3.6.1.4.1.2021.9.1.100";
          config false;
        }
        leaf dskErrorMsg {
          type string {
            length "0 .. 255";
          }
          tailf:snmp-oid "1.3.6.1.4.1.2021.9.1.101";
          config false;
        }
      }
    }
    container laTable {
      config false;
      list laEntry {
        key "laIndex";
        tailf:sort-order "snmp";
        config false;
        tailf:snmp-oid "1.3.6.1.4.1.2021.10";
        leaf laIndex {
          type laIndexType;
          tailf:snmp-oid "1.3.6.1.4.1.2021.10.1.1";
        }
        leaf laNames {
          type string {
            length "0 .. 255";
          }
          tailf:snmp-oid "1.3.6.1.4.1.2021.10.1.2";
          config false;
        }
        leaf laLoad {
          type string {
            length "0 .. 255";
          }
          tailf:snmp-oid "1.3.6.1.4.1.2021.10.1.3";
          config false;
        }
        leaf laConfig {
          type string {
            length "0 .. 255";
          }
          tailf:snmp-oid "1.3.6.1.4.1.2021.10.1.4";
          config false;
        }
        leaf laLoadInt {
          type int32;
          tailf:snmp-oid "1.3.6.1.4.1.2021.10.1.5";
          config false;
        }
        leaf laLoadFloat {
          type Float;
          tailf:snmp-oid "1.3.6.1.4.1.2021.10.1.6";
          config false;
        }
        leaf laErrorFlag {
          type int32;
          tailf:snmp-oid "1.3.6.1.4.1.2021.10.1.100";
          config false;
        }
        leaf laErrMessage {
          type string {
            length "0 .. 255";
          }
          tailf:snmp-oid "1.3.6.1.4.1.2021.10.1.101";
          config false;
        }
      }
    }
    container fileTable {
      config false;
      list fileEntry {
        key "fileIndex";
        tailf:sort-order "snmp";
        config false;
        tailf:snmp-oid "1.3.6.1.4.1.2021.15";
        leaf fileIndex {
          type fileIndexType;
          tailf:snmp-oid "1.3.6.1.4.1.2021.15.1.1";
        }
        leaf fileName {
          type string {
            length "0 .. 255";
          }
          tailf:snmp-oid "1.3.6.1.4.1.2021.15.1.2";
          config false;
        }
        leaf fileSize {
          type int32;
          tailf:snmp-oid "1.3.6.1.4.1.2021.15.1.3";
          config false;
        }
        leaf fileMax {
          type int32;
          tailf:snmp-oid "1.3.6.1.4.1.2021.15.1.4";
          config false;
        }
        leaf fileErrorFlag {
          type SNMPv2-TC:TruthValue;
          tailf:snmp-oid "1.3.6.1.4.1.2021.15.1.100";
          config false;
        }
        leaf fileErrorMsg {
          type string {
            length "0 .. 255";
          }
          tailf:snmp-oid "1.3.6.1.4.1.2021.15.1.101";
          config false;
        }
      }
    }
    container mrTable {
      config false;
      list mrEntry {
        key "mrIndex";
        tailf:sort-order "snmp-implied";
        config false;
        tailf:snmp-oid "1.3.6.1.4.1.2021.102";
        leaf mrIndex {
          type yang:object-identifier;
          tailf:snmp-oid "1.3.6.1.4.1.2021.102.1.1";
        }
        leaf mrModuleName {
          type string {
            length "0 .. 255";
          }
          tailf:snmp-oid "1.3.6.1.4.1.2021.102.1.2";
          config false;
        }
      }
    }
  }
  typedef Float {
    type tailf:hex-list {
      tailf:value-length "7";
    }
  }
  typedef prIndexType {
    type int32 {
      range "0 .. 65535";
    }
  }
  typedef extIndexType {
    type int32 {
      range "0 .. 65535";
    }
  }
  typedef dskIndexType {
    type int32 {
      range "0 .. 65535";
    }
  }
  typedef laIndexType {
    type int32 {
      range "0 .. 3";
    }
  }
  typedef fileIndexType {
    type int32 {
      range "0 .. 2147483647";
    }
  }
}
