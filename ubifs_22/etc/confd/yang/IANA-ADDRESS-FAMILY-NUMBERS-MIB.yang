module IANA-ADDRESS-FAMILY-NUMBERS-MIB {
  namespace "http://tail-f.com/ns/mibs/IANA-ADDRESS-FAMILY-NUMBERS-MIB/201309250000Z";
  prefix IANA_ADDRESS_FAMILY_NUMBERS_MIB;
  tailf:id "";
  tailf:snmp-mib-module-name "IANA-ADDRESS-FAMILY-NUMBERS-MIB";
  import tailf-common {
    prefix tailf;
  }
  revision 2013-09-25 {
    description
      "";
  }
  typedef AddressFamilyNumbers {
    type enumeration {
      enum "other" {
        value 0;
      }
      enum "ipV4" {
        value 1;
      }
      enum "ipV6" {
        value 2;
      }
      enum "nsap" {
        value 3;
      }
      enum "hdlc" {
        value 4;
      }
      enum "bbn1822" {
        value 5;
      }
      enum "all802" {
        value 6;
      }
      enum "e163" {
        value 7;
      }
      enum "e164" {
        value 8;
      }
      enum "f69" {
        value 9;
      }
      enum "x121" {
        value 10;
      }
      enum "ipx" {
        value 11;
      }
      enum "appleTalk" {
        value 12;
      }
      enum "decnetIV" {
        value 13;
      }
      enum "banyanVines" {
        value 14;
      }
      enum "e164withNsap" {
        value 15;
      }
      enum "dns" {
        value 16;
      }
      enum "distinguishedName" {
        value 17;
      }
      enum "asNumber" {
        value 18;
      }
      enum "xtpOverIpv4" {
        value 19;
      }
      enum "xtpOverIpv6" {
        value 20;
      }
      enum "xtpNativeModeXTP" {
        value 21;
      }
      enum "fibreChannelWWPN" {
        value 22;
      }
      enum "fibreChannelWWNN" {
        value 23;
      }
      enum "gwid" {
        value 24;
      }
      enum "afi" {
        value 25;
      }
      enum "mplsTpSectionEndpointIdentifier" {
        value 26;
      }
      enum "mplsTpLspEndpointIdentifier" {
        value 27;
      }
      enum "mplsTpPseudowireEndpointIdentifier" {
        value 28;
      }
      enum "eigrpCommonServiceFamily" {
        value 16384;
      }
      enum "eigrpIpv4ServiceFamily" {
        value 16385;
      }
      enum "eigrpIpv6ServiceFamily" {
        value 16386;
      }
      enum "lispCanonicalAddressFormat" {
        value 16387;
      }
      enum "bgpLs" {
        value 16388;
      }
      enum "fortyeightBitMac" {
        value 16389;
      }
      enum "sixtyfourBitMac" {
        value 16390;
      }
      enum "oui" {
        value 16391;
      }
      enum "mac24" {
        value 16392;
      }
      enum "mac40" {
        value 16393;
      }
      enum "ipv664" {
        value 16394;
      }
      enum "rBridgePortID" {
        value 16395;
      }
      enum "reserved" {
        value 65535;
      }
    }
  }
}
