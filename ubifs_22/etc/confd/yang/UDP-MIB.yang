module UDP-MIB {
  namespace "http://tail-f.com/ns/mibs/UDP-MIB/200505200000Z";
  prefix UDP_MIB;
  tailf:id "";
  tailf:snmp-mib-module-name "UDP-MIB";
  import ietf-yang-types {
    prefix yang;
  }
  import ietf-inet-types {
    prefix inet;
  }
  import tailf-common {
    prefix tailf;
  }
  import INET-ADDRESS-MIB {
    prefix INET-ADDRESS-MIB;
  }
  revision 2005-05-20 {
    description
      "";
  }
  container UDP-MIB {
    container udp {
      tailf:snmp-oid "1.3.6.1.2.1.7";
      config false;
      leaf udpInDatagrams {
        type yang:counter32;
        tailf:snmp-oid "1.3.6.1.2.1.7.1";
        config false;
      }
      leaf udpNoPorts {
        type yang:counter32;
        tailf:snmp-oid "1.3.6.1.2.1.7.2";
        config false;
      }
      leaf udpInErrors {
        type yang:counter32;
        tailf:snmp-oid "1.3.6.1.2.1.7.3";
        config false;
      }
      leaf udpOutDatagrams {
        type yang:counter32;
        tailf:snmp-oid "1.3.6.1.2.1.7.4";
        config false;
      }
      leaf udpHCInDatagrams {
        type yang:counter64;
        tailf:snmp-oid "1.3.6.1.2.1.7.8";
        config false;
      }
      leaf udpHCOutDatagrams {
        type yang:counter64;
        tailf:snmp-oid "1.3.6.1.2.1.7.9";
        config false;
      }
    }
    container udpTable {
      config false;
      list udpEntry {
        key "udpLocalAddress udpLocalPort";
        tailf:sort-order "snmp";
        config false;
        tailf:snmp-oid "1.3.6.1.2.1.7.5";
        leaf udpLocalAddress {
          type inet:ipv4-address;
          tailf:snmp-oid "1.3.6.1.2.1.7.5.1.1";
        }
        leaf udpLocalPort {
          type udpLocalPortType;
          tailf:snmp-oid "1.3.6.1.2.1.7.5.1.2";
        }
      }
    }
    container udpEndpointTable {
      config false;
      list udpEndpointEntry {
        key "udpEndpointLocalAddressType udpEndpointLocalAddress udpEndpointLocalPort udpEndpointRemoteAddressType udpEndpointRemoteAddress udpEndpointRemotePort udpEndpointInstance";
        tailf:sort-order "snmp";
        config false;
        tailf:snmp-oid "1.3.6.1.2.1.7.7";
        leaf udpEndpointLocalAddressType {
          type INET-ADDRESS-MIB:InetAddressType;
          tailf:snmp-oid "1.3.6.1.2.1.7.7.1.1";
        }
        leaf udpEndpointLocalAddress {
          type INET-ADDRESS-MIB:InetAddress;
          tailf:snmp-oid "1.3.6.1.2.1.7.7.1.2";
        }
        leaf udpEndpointLocalPort {
          type INET-ADDRESS-MIB:InetPortNumber;
          tailf:snmp-oid "1.3.6.1.2.1.7.7.1.3";
        }
        leaf udpEndpointRemoteAddressType {
          type INET-ADDRESS-MIB:InetAddressType;
          tailf:snmp-oid "1.3.6.1.2.1.7.7.1.4";
        }
        leaf udpEndpointRemoteAddress {
          type INET-ADDRESS-MIB:InetAddress;
          tailf:snmp-oid "1.3.6.1.2.1.7.7.1.5";
        }
        leaf udpEndpointRemotePort {
          type INET-ADDRESS-MIB:InetPortNumber;
          tailf:snmp-oid "1.3.6.1.2.1.7.7.1.6";
        }
        leaf udpEndpointInstance {
          type udpEndpointInstanceType;
          tailf:snmp-oid "1.3.6.1.2.1.7.7.1.7";
        }
        leaf udpEndpointProcess {
          type uint32;
          tailf:snmp-oid "1.3.6.1.2.1.7.7.1.8";
          config false;
        }
      }
    }
  }
  typedef udpLocalPortType {
    type int32 {
      range "0 .. 65535";
    }
  }
  typedef udpEndpointInstanceType {
    type uint32 {
      range "1 .. 4294967295";
    }
  }
}
