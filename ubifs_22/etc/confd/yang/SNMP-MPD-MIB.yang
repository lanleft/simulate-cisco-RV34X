module SNMP-MPD-MIB {
  namespace "http://tail-f.com/ns/mibs/SNMP-MPD-MIB/200210140000Z";
  prefix SNMP_MPD_MIB;
  tailf:id "";
  tailf:snmp-mib-module-name "SNMP-MPD-MIB";
  import ietf-yang-types {
    prefix yang;
  }
  import tailf-common {
    prefix tailf;
  }
  revision 2002-10-14 {
    description
      "";
  }
  container SNMP-MPD-MIB {
    config false;
    container snmpMPDStats {
      tailf:snmp-oid "1.3.6.1.6.3.11.2.1";
      leaf snmpUnknownSecurityModels {
        type yang:counter32;
        tailf:snmp-oid "1.3.6.1.6.3.11.2.1.1";
        config false;
      }
      leaf snmpInvalidMsgs {
        type yang:counter32;
        tailf:snmp-oid "1.3.6.1.6.3.11.2.1.2";
        config false;
      }
      leaf snmpUnknownPDUHandlers {
        type yang:counter32;
        tailf:snmp-oid "1.3.6.1.6.3.11.2.1.3";
        config false;
      }
    }
  }
}
