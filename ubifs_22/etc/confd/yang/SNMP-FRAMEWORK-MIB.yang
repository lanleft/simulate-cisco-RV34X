module SNMP-FRAMEWORK-MIB {
  namespace "http://tail-f.com/ns/mibs/SNMP-FRAMEWORK-MIB/200210140000Z";
  prefix SNMP_FRAMEWORK_MIB;
  tailf:id "";
  tailf:snmp-mib-module-name "SNMP-FRAMEWORK-MIB";
  import tailf-common {
    prefix tailf;
  }
  revision 2002-10-14 {
    description
      "";
  }
  container SNMP-FRAMEWORK-MIB {
    config false;
    container snmpEngine {
      tailf:snmp-oid "1.3.6.1.6.3.10.2.1";
      leaf snmpEngineID {
        type SnmpEngineID;
        tailf:snmp-oid "1.3.6.1.6.3.10.2.1.1";
        config false;
      }
      leaf snmpEngineBoots {
        type snmpEngineBootsType;
        tailf:snmp-oid "1.3.6.1.6.3.10.2.1.2";
        config false;
      }
      leaf snmpEngineTime {
        type snmpEngineTimeType;
        tailf:snmp-oid "1.3.6.1.6.3.10.2.1.3";
        config false;
      }
      leaf snmpEngineMaxMessageSize {
        type snmpEngineMaxMessageSizeType;
        tailf:snmp-oid "1.3.6.1.6.3.10.2.1.4";
        config false;
      }
    }
  }
  typedef SnmpEngineID {
    type tailf:hex-list {
      pattern "(((([0-9A-Fa-f]{2}):){4,31})([0-9A-Fa-f]{2}))";
      tailf:value-length "5 .. 32";
    }
  }
  typedef SnmpSecurityModel {
    type int32 {
      range "0 .. 2147483647";
    }
  }
  typedef SnmpMessageProcessingModel {
    type int32 {
      range "0 .. 2147483647";
    }
  }
  typedef SnmpSecurityLevel {
    type enumeration {
      enum "noAuthNoPriv" {
        value 1;
      }
      enum "authNoPriv" {
        value 2;
      }
      enum "authPriv" {
        value 3;
      }
    }
  }
  typedef SnmpAdminString {
    type string {
      length "min .. 255";
    }
  }
  typedef snmpEngineBootsType {
    type int32 {
      range "1 .. 2147483647";
    }
  }
  typedef snmpEngineTimeType {
    type int32 {
      range "0 .. 2147483647";
    }
  }
  typedef snmpEngineMaxMessageSizeType {
    type int32 {
      range "484 .. 2147483647";
    }
  }
}
